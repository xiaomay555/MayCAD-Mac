; MayCAD Mac portable public module.
(if (not(member "CL:EMIT"(atoms-family 1)))
 (load (may:resource "may-curtain.lsp")))
(if(not *ed:offset*)(setq *ed:offset* 50.0))
(setq *ed:layer* (may:layer "led"))
(if(not(member *ed:kind* '("Dash" "LED")))(setq *ed:kind* "Dash"))
(if(not *ed:side*)(setq *ed:side* 1.0))
(defun ed:accept (/ off)
 (setq off(distof(get_tile "offset")2))
 (cond
  ((or(not off)(< off 0.0))(set_tile "error" "离基线距离须为0或正数。"))
  ((and(tblsearch "LAYER" (may:layer "led"))(not(cl:layer-ok (may:layer "led"))))
   (set_tile "error" "灯带图层 已关闭、冻结或锁定，请先恢复该层。"))
  (T(setq *ed:offset* off *ed:layer* (may:layer "led")
     *ed:kind*(if(= (get_tile "kind")"1")"LED""Dash"))(done_dialog 1))))
(defun ed:settings (/ src dst line temp id result replacements pair)
 (setq replacements(list(cons "$OFFSET$"(rtos *ed:offset* 2 2))
   (cons "$KIND$"(if(= *ed:kind* "LED")"1""0"))))
 (setq temp (may:temp-ui "edd")
  src(open (may:resource "may-led.dcl") "r" "utf8") dst(open temp "w" "utf8"))
 (while(setq line(read-line src))
  (foreach pair replacements(setq line(vl-string-subst(cdr pair)(car pair)line)))
  (write-line line dst))
 (close src)(close dst)
 (setq id(load_dialog temp))
 (if(and (> id 0)(new_dialog "may_led" id))
  (progn(action_tile "accept" "(ed:accept)")(action_tile "cancel" "(done_dialog 0)")(setq result(start_dialog))))
 (if(and id(> id 0))(unload_dialog id))
 (= result 1))
(defun ed:linetype-name () (if(= *ed:kind* "LED")"LED_LINE""M-DASHDOT"))
(defun ed:linetype (/ name)
 (setq name(ed:linetype-name))
 (cond
  ((tblsearch "LTYPE" name) T)
  ((= name "M-DASHDOT")
   (entmake '((0 . "LTYPE")(100 . "AcDbSymbolTableRecord")(100 . "AcDbLinetypeTableRecord")
   (2 . "M-DASHDOT")(70 . 0)(3 . "__ . __ . __ . __ . __")(72 . 65)(73 . 4)(40 . 5.0)
   (49 . 2.5)(74 . 0)(49 . -1.25)(74 . 0)(49 . 0.0)(74 . 0)(49 . -1.25)(74 . 0))))
  ((tblobjname "STYLE" "Standard")
   (command-s "_.-LINETYPE" "_Load" "LED_LINE"
    (may:resource "may-led.lin") "")
   (if(tblsearch "LTYPE" "LED_LINE")T))))
(defun ed:layer-ready ()(may:prepare "led"))
(defun ed:emit (p q offset side / len ux uy a b lt lts factor)
 (setq len(distance(list(car p)(cadr p))(list(car q)(cadr q)))
       ux(/(- (car q)(car p))len) uy(/(- (cadr q)(cadr p))len)
       a(list(- (car p)(* side uy offset))(+ (cadr p)(* side ux offset)))
       b(list(- (car q)(* side uy offset))(+ (cadr q)(* side ux offset)))
       lt(ed:linetype-name) lts(max 1e-6(getvar "LTSCALE"))
       factor(/(if(= lt "LED_LINE")500.0 25.0)lts))
 (if(entmake(list '(0 . "LWPOLYLINE") '(100 . "AcDbEntity") (cons 8(may:layer "led"))
   (cons 6 lt) '(62 . 256) '(370 . -1)(cons 48 factor)
   '(100 . "AcDbPolyline") '(90 . 2) '(70 . 128)(cons 38(caddr p))
   (cons 10 a)(cons 10 b))) (entlast)))
(defun ed:make (p q offset layer side / len)
 (cond
  ((or(not p)(not q)(not(equal(caddr p)(caddr q)1e-6)))
   (princ "\n两点须在同一水平面，本次未生成。")nil)
  ((or(not offset)(< offset 0.0)(not(member side '(-1.0 1.0))))
   (princ "\n灯带参数无效，本次未生成。")nil)
  ((and(tblsearch "LAYER" (may:layer "led"))(not(cl:layer-ok (may:layer "led"))))
   (princ "\n灯带图层 已关闭、冻结或锁定，本次未生成。")nil)
  (T
   (setq len(distance(list(car p)(cadr p))(list(car q)(cadr q))))
   (if(> len 1e-6)
    (progn
     (if(and(ed:linetype)(ed:layer-ready))
      (ed:emit p q offset side)
      (progn(princ "\n本次未生成：无法准备规范图层或线型。")nil)))
    (progn(princ "\n两点不能重合，本次未生成。")nil)))))
(defun c:EDD (/ *error* p q got stop undo result)
 (defun *error* (msg)
  (if undo(command-s "_.UNDO" "_End"))
  (if(and msg(not(wcmatch(strcase msg)"*CANCEL*,*QUIT*,*EXIT*,*取消*,*中断*")))(princ(strcat "\n" msg)))
  (princ))
 (may:prepare "led")
 (if(ed:settings)
  (progn
   (princ "\n点基线两端只画灯带，可连续绘制；F反向、S设置，空格结束。")
   (while(not stop)
    (initget "S F")
    (setq got(getpoint "\n灯带基线起点 [设置(S)/反向(F)]："))
    (cond
     ((and(= 'STR(type got))(= got "S"))(ed:settings))
     ((and(= 'STR(type got))(= got "F"))(setq *ed:side*(- *ed:side*)))
     ((not got)(setq stop T))
     (T
      (setq p(trans got 1 0) q nil)
      (while(and(not q)(not stop))
       (initget "S F")
       (setq got(getpoint(trans p 0 1)"\n灯带基线终点 [设置(S)/反向(F)]："))
       (cond
        ((and(= 'STR(type got))(= got "S"))(ed:settings))
        ((and(= 'STR(type got))(= got "F"))(setq *ed:side*(- *ed:side*)))
        ((not got)(setq stop T))
        (T(setq q(trans got 1 0)))))
      (if q
       (progn
        (command-s "_.UNDO" "_Begin")(setq undo T)
        (setq result(ed:make p q *ed:offset* *ed:layer* *ed:side*))
        (command-s "_.UNDO" "_End")(setq undo nil)
        (if result(princ "\n灯带完成。")))))))))
 (princ))
(princ)

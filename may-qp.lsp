; MayCAD Mac portable public module.
(if (not *qp:folder*) (setq *qp:folder* (strcat(getenv "HOME")"/Desktop")))
(if (not *qp:format*) (setq *qp:format* 0))
(if (not *qp:paper*) (setq *qp:paper* 1))
(if (not *qp:ctb*) (setq *qp:ctb* "acad.ctb"))
(if (not *qp:scale*) (setq *qp:scale* 0.0))
(if (not *qp:pad*) (setq *qp:pad* 100.0))
(setq qp:root may:cache)
(defun qp:fail (msg) (princ(strcat "\nQP已停止：" msg))(exit))
(defun qp:value (code data fallback / v)
 (if (setq v(assoc code data)) (cdr v) fallback))
(defun qp:rect (en / d pts pair pt low high edges ok w h lastpt uniq)
 (setq d(entget en) ok T)
 (if (and (= (qp:value 0 d "") "LWPOLYLINE")
          (= 1(logand 1(qp:value 70 d 0))) (= 4(qp:value 90 d 0))
          (= 0(qp:value 67 d 0))
          (equal(qp:value 210 d '(0.0 0.0 1.0))'(0.0 0.0 1.0)1e-8)
          (equal(qp:value 38 d 0.0)0.0 1e-8)
          (equal(qp:value 39 d 0.0)0.0 1e-8))
  (progn
   (foreach pair d
    (cond
     ((= (car pair)10)(setq pts(append pts(list(cdr pair)))))
     ((member(car pair)'(40 41 42 43))
      (if (not(equal(cdr pair)0.0 1e-8))(setq ok nil)))))
   (if (= (length pts)4)
    (progn
     (setq low(list(apply 'min(mapcar 'car pts))(apply 'min(mapcar 'cadr pts)))
           high(list(apply 'max(mapcar 'car pts))(apply 'max(mapcar 'cadr pts)))
           w(- (car high)(car low)) h(- (cadr high)(cadr low))
           lastpt(last pts))
     (foreach pt pts
      (if (not(or(and(equal(car pt)(car lastpt)1e-6)
                        (not(equal(cadr pt)(cadr lastpt)1e-6)))
                  (and(equal(cadr pt)(cadr lastpt)1e-6)
                        (not(equal(car pt)(car lastpt)1e-6))))) (setq ok nil))
      (if (vl-some '(lambda(q)(equal pt q 1e-6)) uniq)(setq ok nil))
      (setq uniq(cons pt uniq) lastpt pt))
     (if (and ok (> w 1e-6)(> h 1e-6))
      (list en low high w h (qp:value 8 d "0"))))))))
(defun qp:contains (outer inner / lo hi ilo ihi)
 (setq lo(nth 1 outer) hi(nth 2 outer) ilo(nth 1 inner) ihi(nth 2 inner))
 (and (<= (car lo)(+ (car ilo)1e-6))
      (<= (cadr lo)(+ (cadr ilo)1e-6))
      (>= (car hi)(- (car ihi)1e-6))
      (>= (cadr hi)(- (cadr ihi)1e-6))
      (not(and(equal lo ilo 1e-6)(equal hi ihi 1e-6)))))
(defun qp:collect (ss / i rows result r candidate)
 (setq i 0)
 (if ss(repeat(sslength ss)
  (setq r(qp:rect(ssname ss i)) i(1+ i))
  (if(and r(not(vl-some '(lambda(q)
        (and(equal(nth 1 q)(nth 1 r)1e-6)(equal(nth 2 q)(nth 2 r)1e-6)))rows)))
   (setq rows(cons r rows)))))
 (foreach candidate rows
  (if(not(vl-some '(lambda(q)(qp:contains q candidate))rows))
   (setq result(cons candidate result))))
 (vl-sort result
  '(lambda(a b)
    (if (<(abs(- (cadr(nth 2 a))(cadr(nth 2 b))))(* 0.01(nth 4 a)))
     (<(car(nth 1 a))(car(nth 1 b)))
     (>(cadr(nth 2 a))(cadr(nth 2 b)))))))
(defun qp:escape (s / c out)
 (setq out "")
 (foreach c(vl-string->list s)
  (setq out(strcat out(cond((= c 92)"\\\\")((= c 34)"\\\"")
              ((= c 10)"\\n")(T(chr c)))))) out)
(defun qp:style-dir () (getenv "PrinterStyleSheetDir"))
(defun qp:accept (/ folder scale pad idx)
 (setq folder(vl-string-trim " \t\n"(get_tile "folder"))
       scale(distof(get_tile "scale")2) pad(distof(get_tile "pad")2)
       idx(atoi(get_tile "ctb")))
 (cond
  ((or (= folder "")(/= (substr folder 1 1)"/"))
   (set_tile "error" "请填写以 / 开头的本机绝对路径。"))
  ((or(not scale)(< scale 0)(not pad)(< pad 0))
   (set_tile "error" "比例和留白应是大于或等于0的数字。"))
  ((not(nth idx qp:ctbs))(set_tile "error" "请选择有效CTB。"))
  (T(setq *qp:folder* folder *qp:scale* scale *qp:pad* pad
           *qp:format*(atoi(get_tile "format")) *qp:paper*(atoi(get_tile "paper"))
           *qp:ctb*(nth idx qp:ctbs))(done_dialog 1))))
(defun qp:settings (/ src dst s id status styles idx pair)
 (setq qp:ctbs(acad_strlsort(vl-directory-files(qp:style-dir)"*.ctb"1))
       idx(vl-position *qp:ctb* qp:ctbs) styles "")
 (if (not idx)(setq idx 0))
 (foreach s qp:ctbs(setq styles(strcat styles(if(= styles "")"""\\n")(qp:escape s))))
 (if(= *qp:folder* "")(setq *qp:folder* (strcat(getenv "HOME")"/Desktop")))
 (setq src(open(may:resource "may-qp.dcl")"r""utf8")
       dst(open(strcat qp:root "qp-active.dcl")"w""utf8"))
 (while(setq s(read-line src))
  (foreach pair(list(cons "$FOLDER$"(qp:escape *qp:folder*))
      (cons "$FORMAT$"(itoa *qp:format*)) (cons "$PAPER$"(itoa *qp:paper*))
      (cons "$CTBS$" styles)(cons "$CTB$"(itoa idx))
      (cons "$SCALE$"(rtos *qp:scale* 2 2))(cons "$PAD$"(rtos *qp:pad* 2 2)))
   (setq s(vl-string-subst(cdr pair)(car pair)s)))
  (write-line s dst))
 (close src)(close dst)
 (setq id(load_dialog(strcat qp:root "qp-active.dcl")))
 (if(and (> id 0)(new_dialog "may_qp" id))
  (progn(if qp:notice(set_tile "error" qp:notice))
       (action_tile "accept" "(qp:accept)")(action_tile "cancel" "(done_dialog 0)")
       (setq status(start_dialog))))
 (if(and id(> id 0))(unload_dialog id))
 (= status 1))
(defun qp:mkdir (path / parent)
 (or(vl-file-directory-p path)
    (and(setq parent(vl-filename-directory path))(/= path parent)
       (qp:mkdir parent)(vl-mkdir path))))
(defun qp:wait (file seconds / deadline)
 (setq deadline(+ (getvar "DATE")(/ seconds 86400.0)))
 (while(and(not(findfile file))(<(getvar "DATE")deadline))
  (command-s "_.DELAY" 100))
 (findfile file))
(defun qp:paper ()
 (nth *qp:paper* '("ISO full bleed A4 (297.00 x 210.00 MM)"
 "ISO full bleed A3 (420.00 x 297.00 MM)" "ISO full bleed A2 (594.00 x 420.00 MM)"
 "ISO full bleed A1 (841.00 x 594.00 MM)")))
(defun qp:volume-error (path / cut volume)
 (if(= (substr path 1 9)"/Volumes/")
  (progn
   (setq cut(vl-string-search "/" path 9)
         volume(if cut(substr path 1 cut)path))
   (if(not(vl-file-directory-p volume))
    "输出硬盘未连接，请接入硬盘或改用本机文件夹。"))))
(defun qp:check (rows root / dims row pw ph issue made probe handle)
 (setq issue
  (cond
   ((not rows)"未选中有效图框，请重新框选。")
   ((not(findfile(strcat(getenv "PrinterConfigDir")"/AutoCAD PDF (High Quality Print).pc3")))
    "找不到原生PDF打印机，请检查打印机配置。")
   ((not(findfile(strcat(qp:style-dir)"/" *qp:ctb*)))
    "找不到所选CTB，请重新选择打印样式。")
   ((qp:volume-error root))))
 (setq dims(nth *qp:paper* '((297.0 210.0)(420.0 297.0)(594.0 420.0)(841.0 594.0))))
 (if(and(not issue)(> *qp:scale* 0))
  (foreach row rows
   (setq pw(if(>= (nth 3 row)(nth 4 row))(car dims)(cadr dims))
         ph(if(>= (nth 3 row)(nth 4 row))(cadr dims)(car dims)))
   (if(or(> (+ (nth 3 row)(* 2 *qp:pad*))(* pw *qp:scale*))
         (> (+ (nth 4 row)(* 2 *qp:pad*))(* ph *qp:scale*)))
    (setq issue "当前比例放不进纸张：1:100填100，布满填0，或选更大纸张。"))))
 (if(not issue)
  (progn
   (setq made(vl-catch-all-apply 'qp:mkdir(list root)))
   (if(or(vl-catch-all-error-p made)(not made))
    (setq issue "输出文件夹无法创建，请修改输出路径。")
    (progn
     (setq probe(vl-filename-mktemp "QP-write-" root ".tmp")
           handle(vl-catch-all-apply 'open(list probe "w")))
     (if(or(vl-catch-all-error-p handle)(not handle))
      (setq issue "输出文件夹不可写，请换一个本机文件夹。")
      (progn(close handle)(vl-file-delete probe)))))))
 issue)
(defun qp:preflight (rows root / issue)
 (if(setq issue(qp:check rows root))(qp:fail issue)) T)
(defun qp:one (row dest / lo hi orient)
 (setq lo(mapcar '- (nth 1 row)(list *qp:pad* *qp:pad*))
       hi(mapcar '+ (nth 2 row)(list *qp:pad* *qp:pad*))
       orient(if(>= (nth 3 row)(nth 4 row))"_L""_P"))
 (if(findfile dest)(qp:fail "Output exists; refusing overwrite."))
 (command-s "_.-PLOT" "_Y" "Model" "AutoCAD PDF (High Quality Print).pc3"
  (qp:paper) "_M" orient "_N" "_W" "_non" lo "_non" hi
  (if(= *qp:scale* 0)"_F"(strcat "1="(rtos *qp:scale* 2 8)))
  "_C" "_Y" qp:plot-ctb "_Y" "_A" dest "_N" "_Y")
 (if (not(qp:wait dest 20.0))(qp:fail "PDF not produced; batch stopped."))
 (if (<= (vl-file-size dest)100)(qp:fail "Empty PDF; batch stopped."))
 dest)
(defun qp:run (rows root / saved folder stem suffix index row file manifest handle jpgstat job result count staging pdf jpg)
 (qp:preflight rows root)
 (setq saved(mapcar '(lambda(v)(cons v(getvar v)))
    '("CMDECHO" "OSMODE"))
       qp:saved saved)
 (foreach pair '(("CMDECHO" . 0)("OSMODE" . 0))
  (setvar(car pair)(cdr pair)))
 (if(not(qp:mkdir root))(qp:fail "Cannot create output folder."))
 (setq stem(strcat "QP_"(vl-string-translate ".""_"(rtos(getvar "CDATE")2 6)))
       suffix 0 folder(strcat root "/" stem))
 (while(vl-file-directory-p folder)
  (setq suffix(1+ suffix) folder(strcat root "/" stem "_"(itoa suffix))))
 (if(not(vl-mkdir folder))(qp:fail "Cannot create batch folder."))
 (setq qp:plot-ctb *qp:ctb*)
 (if(vl-some '(lambda(c)(> c 127))(vl-string->list *qp:ctb*))
  (progn
   (setq qp:plot-ctb(strcat "QP-" stem "-"(itoa suffix)".ctb")
         qp:temp-style(strcat(qp:style-dir)"/" qp:plot-ctb))
   (if(not(vl-file-copy(strcat(qp:style-dir)"/" *qp:ctb*)qp:temp-style))
    (qp:fail "Could not create temporary CTB alias."))))
 (setq handle(open(strcat folder "/QP-manifest.txt")"w""utf8") index 1)
 (write-line(strcat "Drawing: "(getvar "DWGPREFIX")(getvar "DWGNAME"))handle)
 (write-line(strcat "Style: " *qp:ctb* "; scale: "(rtos *qp:scale* 2 4))handle)
 (close handle)
 (foreach row rows
  (setq file(strcat folder "/Sheet_"(if(< index 10)"00"(if(< index 100)"0"""))(itoa index)".pdf"))
  (princ(strcat "\nQP "(itoa index)"/"(itoa(length rows))))
  (qp:one row file)
  (setq handle(open(strcat folder "/QP-manifest.txt")"a""utf8"))
  (write-line(strcat(vl-filename-base file)" | frame="(cdr(assoc 5(entget(car row)))))handle)
  (close handle)(setq index(1+ index)))
 (if(= *qp:format* 1)
  (progn
   (setq staging(strcat qp:root "qp-jobs/" stem "_"(itoa suffix)))
   (if(not(qp:mkdir staging))(qp:fail "Cannot create JPG staging folder."))
   (foreach pdf(vl-directory-files folder "*.pdf"1)
    (if(not(vl-file-copy(strcat folder "/" pdf)(strcat staging "/" pdf)))
     (qp:fail "Could not stage PDF for JPG conversion.")))
   (setq manifest(strcat qp:root "qp-current-job.txt"))
   (setq handle(open manifest "w""utf8"))
   (write-line staging handle)(close handle)
   (setq job(startapp(may:resource "QP-Render.app")))
   (if(not job)(qp:fail "PDF finished; macOS JPG helper failed to start."))
   (setq jpgstat(strcat staging "/QP-JPG-status.txt"))
   (if(qp:wait jpgstat 20.0)
    (progn(setq handle(open jpgstat "r""utf8") result(read-line handle))(close handle)
      (if(/= (substr result 1 2)"OK")(qp:fail(strcat "PDF已完成；JPG转换失败：" result))))
    (qp:fail "PDF finished; JPG conversion timed out. Staging files kept."))
   (foreach pdf(vl-directory-files folder "*.pdf"1)
    (setq jpg(strcat(vl-filename-base pdf)".jpg"))
    (if(not(vl-file-copy(strcat staging "/" jpg)(strcat folder "/" jpg)))
     (qp:fail "PDF finished; could not copy converted JPG to output folder.")))
   (foreach file(vl-directory-files staging nil 1)
    (vl-file-delete(strcat staging "/" file)))))
 (if qp:temp-style(vl-file-delete qp:temp-style)) (setq qp:temp-style nil)
 (foreach pair saved(setvar(car pair)(cdr pair))) (setq qp:saved nil)
 (setq *qp:last-folder* folder)
 (princ(strcat "\nQP完成："(itoa(length rows))"张；" folder))
 folder)
(defun c:QP (/ *error* ss rows ready qp:notice qp:saved qp:temp-style qp:plot-ctb)
 (defun *error* (msg)
  (if qp:saved(foreach pair qp:saved(setvar(car pair)(cdr pair))))
  (if qp:temp-style(vl-file-delete qp:temp-style))
  (if(and msg(not(wcmatch(strcase msg)"*CANCEL*,*QUIT*,*BREAK*")))
   (princ(strcat "\nQP已停止：" msg))) (princ))
 (cond
  ((or(/= (getvar "TILEMODE")1)(/= (getvar "WORLDUCS")1)
       (not(equal(getvar "VIEWDIR")'(0.0 0.0 1.0)1e-6))
       (not(equal(getvar "VIEWTWIST")0.0 1e-6)))
   (princ "\n请在模型空间的世界UCS俯视图运行QP。"))
  ((/= (getvar "PSTYLEMODE")1)(princ "\n当前图使用STB；此版QP需CTB图形。"))
  (T
   (setq ss(ssget "_I" '((0 . "LWPOLYLINE")(410 . "Model"))))
   (if(qp:settings)
    (progn
     (if(not ss)
      (progn(princ "\n框选本次要导出的图框，可继续加选/减选，空格确认：")
       (setq ss(ssget '((0 . "LWPOLYLINE")(410 . "Model"))))))
     (if ss
      (progn
       (sssetfirst nil nil)
       (setq rows(qp:collect ss))
       (if rows
        (progn(princ(strcat "\n本次选中 "(itoa(length rows))" 个图框。"))
         (setq ready T)
         (while(and ready(setq qp:notice(qp:check rows *qp:folder*)))
          (princ(strcat "\n" qp:notice " 已保留选中图框，返回设置。"))
          (setq ready(qp:settings)))
         (if ready(qp:run rows *qp:folder*)
          (princ "\n已取消本次打印。")))
        (princ "\n选择中没有有效矩形图框。请框入完整外框；弧线/旋转框不支持。"))))))))
 (princ))
(princ)

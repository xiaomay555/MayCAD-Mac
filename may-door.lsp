; MayCAD Mac portable public module.
(setq mm:profile-casing '(("P" "0" ((0 0)(60 0)(60 20)(15 20)(0 10))T)))
(setq mm:profile-flatcasing '(("P" "0" ((0 0)(60 0)(60 20)(0 20))T)))
(setq mm:profile-handle '(("P" "0" ((-12 0)(12 0)(12 12)(-12 12))T)
 ("P" "0" ((-5 12)(5 12)(5 50)(85 50)(85 60)(-5 60))T)))
(setq mm:profile-hinge '(("C" "0" (2.5 2.5)2.5)("P" "0" ((0 0)(0 -25)(3 -25)(3 0))T)))
(setq mm:profile-seal '(("P" "0" ((0 0)(5 0)(5 5)(0 5))T)))
(setq mm:ui-file(may:temp-ui "mm"))

(if(not *mm:mode*)(setq *mm:mode* "I"))
(if(not *mm:leaves*)(setq *mm:leaves* 1))
(if(not *mm:angle*)(setq *mm:angle* (/ pi 2.0)))
(setq *mm:double*(= *mm:leaves* 2))
(setq *mm:leaf* 45.0 *mm:trim* 60.0 *mm:return* 20.0 *mm:gap* 3.0)
(if(not *mm:doorlayer*)(setq *mm:doorlayer* (may:layer "door")))
(if(not *mm:framelayer*)(setq *mm:framelayer* (may:layer "door-frame")))
(if(not *mm:headerlayer*)(setq *mm:headerlayer* (may:layer "opening")))
(defun mm:xy(p)(list(car p)(cadr p)))
(defun mm:sub(a b)(list(- (car a)(car b))(- (cadr a)(cadr b))))
(defun mm:dot(a b)(+(* (car a)(car b))(* (cadr a)(cadr b))))
(defun mm:scale(a k)(list(* (car a)k)(* (cadr a)k)))
(defun mm:normal(u)(list(- (cadr u))(car u)))
(defun mm:z(p)(if(caddr p)(caddr p)0.0))
(defun mm:basis(a b c mode / t0 n u w vec len)
 (if(and a b(equal(mm:z a)(mm:z b)1e-6)
         (or(mm:two mode)(and c(equal(mm:z a)(mm:z c)1e-6))))
  (if(mm:two mode)
   (progn
    (setq vec(mm:sub b a)len(distance(mm:xy a)(mm:xy b)))
    (if(> len 1e-6)
     (progn(setq u(mm:scale vec(/ 1.0 len)))(list a u(mm:normal u)0.0 len))))
   (progn
    (setq t0(distance(mm:xy a)(mm:xy b)))
    (if(> t0 1e-6)
     (progn
      (setq n(mm:scale(mm:sub b a)(/ 1.0 t0))u(mm:normal n)
            w(mm:dot(mm:sub c a)u))
      (if(< w 0.0)(setq u(mm:scale u -1.0)w(- w)))
      (if(> w 1e-6)(list a u n t0 w))))))))
(defun mm:point(p basis / o u n)
 (setq o(car basis)u(cadr basis)n(caddr basis))
 (list(+ (car o)(* (car p)(car u))(* (cadr p)(car n)))
       (+ (cadr o)(* (car p)(cadr u))(* (cadr p)(cadr n)))(mm:z o)))
(defun mm:local(p basis / d)
 (setq d(mm:sub p(car basis)))
 (list(mm:dot d(cadr basis))(mm:dot d(caddr basis))))
(defun mm:layer-ok(name / r)
 (and(setq r(tblsearch "LAYER" name))(> (cdr(assoc 62 r))0)
     (= 0(logand 21(cdr(assoc 70 r))))))
(defun mm:poly(layer pts closed)(list "P" layer pts closed))
(defun mm:arc(layer centre radius start end)(list "A" layer centre radius start end))





(defun mm:profile-v5 (items pos sx sy rot layer / result item pts bulges p q a b)
 (foreach item items
  (setq pts nil bulges nil)
  (if(= (car item)"P")
   (progn
    (foreach p(caddr item)
     (setq pts(append pts(list(list
      (+ (car pos)(* sx(car p)(cos rot))(- (* sy(cadr p)(sin rot))))
      (+ (cadr pos)(* sx(car p)(sin rot))(* sy(cadr p)(cos rot))))))))
    (foreach b(nth 4 item)(setq bulges(append bulges(list(* b(if(< (* sx sy)0.0)-1.0 1.0))))))
    (setq result(append result(list(list "P" layer pts(cadddr item)bulges)))))
   (progn
    (setq p(caddr item) q(list
      (+ (car pos)(* sx(car p)(cos rot))(- (* sy(cadr p)(sin rot))))
      (+ (cadr pos)(* sx(car p)(sin rot))(* sy(cadr p)(cos rot)))))
    (if(= (car item)"C")
     (setq result(append result(list(list "C" layer q(nth 3 item)))))
     (progn
      (setq a(+ rot(atan(* sy(sin(nth 4 item)))(* sx(cos(nth 4 item)))))
            b(+ rot(atan(* sy(sin(nth 5 item)))(* sx(cos(nth 5 item))))))
      (if(< (* sx sy)0.0)(setq p a a b b p))
      (setq result(append result(list(mm:arc layer q(nth 3 item)a b)))))))))
 result)
(defun mm:box (layer x0 y0 x1 y1)
 (mm:poly layer(list(list x0 y0)(list x1 y0)(list x1 y1)(list x0 y1))T))
(defun mm:mirror (items w / item)
 (mm:profile items(list w 0.0)-1.0 1.0 0.0(cadr(car items))))
(defun mm:orient (items w t0 mirror-x mirror-y / result item)
 (foreach item items
  (setq result(append result(mm:profile(list item)
   (list(if mirror-x w 0.0)(if mirror-y t0 0.0))
   (if mirror-x -1.0 1.0)(if mirror-y -1.0 1.0)0.0(cadr item)))))
 result)
(defun mm:two (mode)(member mode '("N" "S" "L")))
(defun mm:layers-ok (mode)
 (and(mm:layer-ok *mm:doorlayer*)
  (or(= mode "S")(mm:layer-ok *mm:framelayer*))
  (or(not(member mode '("I" "O" "I2" "O2")))(mm:layer-ok *mm:headerlayer*))))
(defun mm:headers (w t0)
 (list(mm:poly *mm:headerlayer*(list '(0.0 0.0)(list w 0.0))nil)
       (mm:poly *mm:headerlayer*(list(list 0.0 t0)(list w t0))nil)))
(defun mm:frame (w t0 mode leaf fl dl / left k d lip)
 (if(= mode "N")
  (progn
   (setq k(if *mm:double* 50.0 45.0)d(if *mm:double* 40.0 27.0)
    lip(if *mm:double* 15.0 13.5))
   (setq left(list(mm:poly fl(list(list k d)(list 0.0 d)(list 0.0(- d))
    (list(+ k lip)(- d))(list(+ k lip)0.0)(list k 0.0))T))))
  (progn
   (setq left(append(list(mm:poly fl(list(list 0.0 t0)(list 30.0 t0)
    (list 30.0(- t0 50.0))(list 40.0(- t0 50.0))'(40.0 0.0)'(0.0 0.0))T))
    (mm:profile mm:profile-casing(list 30.0 t0)-1.0 1.0 0.0 fl)
    (mm:profile mm:profile-casing '(40.0 0.0)-1.0 -1.0 0.0 fl)))
   (if(= mode "I")(setq left(mm:orient left w t0 nil T)))))
 (append left(mm:mirror left w)(if(member mode '("I" "O"))(mm:headers w t0))))
(defun mm:leafspecs (x y radius leaf alpha framed dl side / result outlines lever theta)
 (setq outlines(list(mm:poly dl(list '(0.0 0.0)(list radius 0.0)
  (list radius(- leaf))(list 0.0(- leaf)))T)))
 (if framed
  (progn
   (setq lever(max 20.0(- radius 90.0)))
   (setq outlines(append outlines
    (mm:profile mm:profile-handle(list lever 0.0)-1.0 1.0 0.0 dl)
    (mm:profile mm:profile-handle(list lever(- leaf))1.0 1.0 pi dl)))))
 (setq theta(* side alpha)
  result(mm:profile outlines(list x y)1.0 side theta dl))
 (append result(list(mm:arc dl(list x y)radius(min 0.0 theta)(max 0.0 theta)))))
(defun mm:linked (w layer / i a lo hi y result)
 (setq i 0 a(/ w 3.0))
 (repeat 3
  (setq lo(if(= i 0)0.0(-(* i a)40.0))hi(* (1+ i)a)y(* i -25.0))
  (setq result(append result(list(mm:poly layer
   (list(list lo y)(list(- hi 15.0)y)(list(- hi 15.0)(- y 5.0))
    (list hi(- y 5.0))(list hi(+ y 20.0))(list lo(+ y 20.0)))T))))
  (setq i(1+ i)))result)
(defun mm:sliding (w mode dl / result half arrow)
 (setq half(/ w 2.0)arrow(min 150.0(* w 0.08)))
 (if(= mode "S")
  (list(mm:box dl 0.0 0.0 half 35.0)(mm:box dl half -35.0 w 0.0)
   (mm:poly dl(list(list(- half arrow)17.5)(list(+ half arrow)17.5)(list half 55.0))nil)
   (mm:poly dl(list(list(+ half arrow)-17.5)(list(- half arrow)-17.5)(list half -55.0))nil))
  (mm:linked w *mm:framelayer*)))
(defun mm:layout-v5 (w t0 mode h s leaf trim ret gap dl fl / x y r alpha specs doors second hinge closed opened framed pivot-y low high)
 (if(and(member mode '("I" "O" "N" "S" "L"))(member h '(-1 1))(member s '(-1 1))
  (> w 200.0)(or(mm:two mode)(>= t0 70.0)))
  (if(member mode '("S" "L"))
   (if(> w 400.0)
    (list(mm:orient(mm:sliding w mode dl)w 0.0(= h -1)(= s -1))nil nil nil))
   (progn
    (setq framed(not(= mode "N"))
     leaf(if framed leaf(if *mm:double* 30.0 27.0))
     x(if framed(+ 30.0 gap)(if *mm:double* 50.0 45.0))
     low(if(= mode "O")(- t0 leaf)0.0)
     high(+ low leaf)
     y(if framed(if(= s 1)high low)(if *mm:double* 40.0 27.0))
     r(if *mm:double*(/(- w(* 2.0 x)gap)2.0)(- w(* 2.0 x)))
     alpha(if *mm:angle* *mm:angle* (/ pi 2.0)))
    (if(and(> r(+ leaf 20.0))(> alpha 0.0)(<= alpha(/ pi 2.0)))
     (progn
      (setq specs(mm:frame w t0 mode leaf fl dl)
       doors(mm:leafspecs x y r leaf alpha framed dl(if framed s 1)))
      (if *mm:double*(setq second(mm:orient doors w 0.0 T nil)))
      (setq specs(mm:orient(append specs doors second)w 0.0(= h -1)(and(not framed)(= s -1)))
       pivot-y(if(and(not framed)(= s -1))(- y)y)
       hinge(list(if(= h 1)x(- w x))pivot-y)
       closed(list(+ (car hinge)(* h r))pivot-y)
       opened(list(+ (car hinge)(* h r(cos alpha)))(+ pivot-y(* s r(sin alpha)))))
      (list specs hinge closed opened)))))))
(defun mm:arcpoints (c r a delta / i pts)
 (setq i 0)
 (repeat 33(setq pts(cons(polar c(+ a(* delta(/ i 32.0)))r)pts)i(1+ i)))
 (reverse pts))
(defun mm:spec-points-v5 (spec / points bulges count i p q b dx dy chord centre radius a delta result)
 (if(= (car spec)"P")
  (progn
   (setq points(caddr spec)bulges(nth 4 spec)count(length points)i 0)
   (repeat(if(cadddr spec)count(1- count))
    (setq p(nth i points)q(nth(rem(1+ i)count)points)b(if(and bulges(nth i bulges))(nth i bulges)0.0))
    (if(< (abs b)1e-10)(setq result(append result(list p q)))
     (progn
      (setq dx(- (car q)(car p))dy(- (cadr q)(cadr p))chord(distance p q)
       centre(list(- (/ (+ (car p)(car q))2.0)(* dy(/(- 1.0(* b b))(* 4.0 b))))
                   (+ (/ (+ (cadr p)(cadr q))2.0)(* dx(/(- 1.0(* b b))(* 4.0 b)))))
       radius(/(* chord(+ 1.0(* b b)))(* 4.0(abs b))))
      (setq result(append result(mm:arcpoints centre radius(angle centre p)(* 4.0(atan b)))))))
    (setq i(1+ i)))
   result)
  (progn
   (setq a(if(= (car spec)"C")0.0(nth 4 spec))
    delta(if(= (car spec)"C")(* 2.0 pi)
     (rem(+(* 2.0 pi)(- (nth 5 spec)a))(* 2.0 pi))))
   (mm:arcpoints(caddr spec)(nth 3 spec)a delta))))
(defun mm:emit-v5 (spec basis / data p q a b c u n cross bulges i)
 (setq u(cadr basis)n(caddr basis)cross(-(* (car u)(cadr n))(* (cadr u)(car n))))
 (setq data(list(cons 0(if(= (car spec)"P")"LWPOLYLINE"(if(= (car spec)"C")"CIRCLE""ARC")))
  '(100 . "AcDbEntity")(cons 8(cadr spec))))
 (if(= (car spec)"P")
  (progn
   (setq data(append data(list '(100 . "AcDbPolyline")(cons 90(length(caddr spec)))
    (cons 70(if(cadddr spec)1 0))(cons 38(mm:z(car basis))))))
   (setq i 0 bulges(nth 4 spec))
   (foreach p(caddr spec)
    (setq q(mm:point p basis)data(append data(list(cons 10(mm:xy q)))))
    (if(and bulges(nth i bulges))(setq data(append data(list(cons 42(* cross(nth i bulges)))))))
    (setq i(1+ i))))
  (progn
   (setq c(mm:point(caddr spec)basis)
    data(append data(list '(100 . "AcDbCircle")(cons 10 c)(cons 40(nth 3 spec)))))
   (if(= (car spec)"A")
    (progn
     (setq p(mm:point(polar(caddr spec)(nth 4 spec)(nth 3 spec))basis)
      q(mm:point(polar(caddr spec)(nth 5 spec)(nth 3 spec))basis)
      a(angle c p)b(angle c q))
     (if(< cross 0.0)(setq p a a b b p))
     (setq data(append data(list '(100 . "AcDbArc")(cons 50 a)(cons 51 b))))))))
 (if(nth 6 spec)(setq data(append data(list(cons 62(nth 6 spec))))))
 (entmake data))
(defun mm:discard (/)
 (if mm:building(entmake '((0 . "ENDBLK"))))
 (setq mm:building nil)
 (if(and mm:newblock(tblsearch "BLOCK" mm:newblock))
  (command-s "_.-PURGE" "_Blocks" mm:newblock "_N"))
 (setq mm:newblock nil))
(defun mm:insert (specs basis mode / n name ok item local u normal sign result)
 (setq n 1 name(strcat "MM_" mode "_1"))
 (while(tblsearch "BLOCK" name)(setq n(1+ n)name(strcat "MM_" mode "_"(itoa n))))
 (setq mm:newblock name local(list '(0.0 0.0 0.0)'(1.0 0.0)'(0.0 1.0)0.0 0.0))
 (setq ok(entmake(list '(0 . "BLOCK")'(100 . "AcDbEntity")'(8 . "0")
  '(100 . "AcDbBlockBegin")(cons 2 name)'(70 . 0)'(10 0.0 0.0 0.0))))
 (setq mm:building(if ok T nil))
 (foreach item specs(if ok(setq ok(mm:emit item local))))
 (if mm:building
  (progn(if(not(entmake '((0 . "ENDBLK"))))(setq ok nil))(setq mm:building nil)))
 (if ok
  (progn
   (setq u(cadr basis)normal(caddr basis)sign(if(< (-(* (car u)(cadr normal))(* (cadr u)(car normal)))0.0)-1.0 1.0))
   (if(entmake(list '(0 . "INSERT")'(100 . "AcDbEntity")(cons 8 *mm:doorlayer*)
    '(100 . "AcDbBlockReference")(cons 2 name)(cons 10(car basis))
    '(41 . 1.0)(cons 42 sign)'(43 . 1.0)(cons 50(atan(cadr u)(car u)))))
    (setq result(entlast)))))
 (if result(setq mm:newblock nil)(mm:discard))
 result)
(defun mm:preview(specs basis / spec pts vectors p q)
 (foreach spec specs
  (setq pts(mapcar '(lambda(p)(trans(mm:point p basis)0 1))(mm:spec-points spec)))
  (while(cdr pts)
   (setq p(car pts)q(cadr pts)vectors(cons 3(cons p(cons q vectors)))pts(cdr pts))))
 (redraw)
 (if vectors(grvecs vectors)))
(defun mm:choose(basis mode / ev p local h s oldh olds result layout stop t0 w)
 (setq t0(nth 3 basis)w(nth 4 basis)h 1 s 1)
 (princ "\n移动鼠标确定方向，点击生成；带套门可按I/O切换齐平，Esc取消。")
 (while(not stop)
  (setq ev(grread T 15 0))
  (cond
   ((member(car ev)'(3 5))
    (setq p(trans(cadr ev)1 0)local(mm:local p basis)
          h(if(< (car local)(/ w 2.0))1 -1))
    (if(> (abs(- (cadr local)(/ t0 2.0)))1e-6)
     (setq s(if(> (cadr local)(/ t0 2.0))1 -1)))
    (setq layout(mm:layout w t0 mode h s *mm:leaf* *mm:trim* *mm:return* *mm:gap* *mm:doorlayer* *mm:framelayer*))
    (if layout(mm:preview(car layout)basis))
    (if(= (car ev)3)(setq stop T result(list layout mode))))
   ((= (car ev)2)
    (cond
     ((= (cadr ev)27)(setq stop T))
     ((and(member mode '("I" "O" "I2" "O2"))(member(cadr ev)'(73 105 79 111)))
      (setq mode(strcat(if(member(cadr ev)'(73 105))"I""O")(if(mm2:mode mode)"2""")))
      (setq layout(mm:layout w t0 mode h s *mm:leaf* *mm:trim* *mm:return* *mm:gap* *mm:doorlayer* *mm:framelayer*))
      (if layout(mm:preview(car layout)basis)))))))
 (redraw)
 result)
(defun mm:kind-ui (/ off)
 (setq off(if(member(atoi(get_tile "kind"))'(3 4))1 0))
 (mode_tile "count" off)(mode_tile "angle" off))
(defun mm:accept (/ mode)
 (setq mode(nth(atoi(get_tile "kind"))'("I" "O" "N" "S" "L" "I2" "O2")))
 (if(mm:layers-ok mode)
  (progn(setq *mm:mode* mode
   *mm:leaves*(if(member mode '("S" "L"))1(if(= (get_tile "count")"1")2 1))
   *mm:double*(= *mm:leaves* 2)
   *mm:angle*(if(= (get_tile "angle")"1")(/ pi 6.0)(/ pi 2.0)))
   (done_dialog 1))
  (set_tile "error" "所需门、门套或墙面线图层缺失、关闭、冻结或锁定。")))
(defun mm:settings (/ source target line pair id status idx)
 (setq source(open(may:resource "may-door.dcl")"r""utf8")
  target(open mm:ui-file "w""utf8"))
 (if(and source target)
  (progn
   (setq idx(vl-position *mm:mode* '("I" "O" "N" "S" "L" "I2" "O2")))
   (while(setq line(read-line source))
    (foreach pair(list(cons "$MODE$"(itoa(if idx idx 0)))
     (cons "$COUNT$"(if *mm:double* "1""0"))
     (cons "$ANGLE$"(if(< *mm:angle* 1.0)"1""0")))
     (setq line(vl-string-subst(cdr pair)(car pair)line)))
    (write-line line target))
   (close source)(setq source nil)(close target)(setq target nil)
   (setq id(load_dialog mm:ui-file ))
   (if(and(> id 0)(new_dialog "may_door" id))
    (progn(mm:kind-ui)(action_tile "kind" "(mm:kind-ui)")
     (action_tile "accept" "(mm:accept)")(action_tile "cancel" "(done_dialog 0)")
     (setq status(start_dialog))))
   (if(and id(> id 0))(unload_dialog id))))
 (if source(close source))(if target(close target))
 (= status 1))

(defun mm2:mode (mode)(member mode '("I2" "O2")))
(defun mm2:base (mode)(if(= mode "I2")"I""O"))
(defun mm2:colours (specs colour / result item)
 (foreach item specs(setq result(append result(list(append(list(car item)(cadr item)(caddr item)(nth 3 item)(nth 4 item)(nth 5 item))(list colour))))))result)
(defun mm2:frame (w t0 mode fl / left)
 (setq left(append
  (list(mm:box fl 0.0 0.0 20.0 t0)
   (mm:poly fl(list(list 20.0 t0)(list 40.0 t0)(list 40.0(- t0 10.0))
    (list 30.0(- t0 10.0))(list 30.0(- t0 45.0))(list 20.0(- t0 45.0)))T))
  (mm:profile mm:profile-flatcasing '(20.0 0.0)-1.0 -1.0 0.0 fl)))
 (if(= mode "I2")(setq left(mm:orient left w t0 nil T)))
 (append left(mm:mirror left w)(mm:headers w t0)))

(defun mm2:closed (r dl / result i n step pts)
 (setq result(list(mm:box dl 0.0 0.0 r 45.0)
  (mm:box dl 15.0 8.0(- r 15.0)37.0))
  n(max 1(fix(/(- r 30.0)25.0)))step(/(- r 30.0)n)i 0)
 (repeat(1+ n)
  (setq pts(append pts(list(list(+ 15.0(* i step))8.0)(list(+ 15.0(* i step))37.0)))i(1+ i)))
 (append result(mm2:colours(list(mm:poly dl pts nil))8)))
(defun mm2:leaf (x y r alpha side dl / outlines lever theta)
 (setq outlines(list(mm:poly dl(list '(0.0 0.0)(list r 0.0)(list r -32.0)
  (list(- r 10.0)-32.0)(list(- r 10.0)-45.0)'(10.0 -45.0)'(10.0 -32.0)'(0.0 -32.0))T)))
 (setq lever(max 20.0(- r 90.0)))
 (setq outlines(append(mm2:colours outlines 8)
  (mm:profile mm:profile-handle(list lever 0.0)-1.0 1.0 0.0 dl)))
 (setq theta(* side alpha))
 (append(mm:profile outlines(list x y)1.0 side theta dl)
  (mm2:colours(list(mm:arc dl(list x y)r(min 0.0 theta)(max 0.0 theta)))8)))
(defun mm2:hardware (w t0 mode dl / result)
 (setq result(append
  (mm:profile mm:profile-hinge(list 30.0(- t0 45.0))-1.0 1.0 pi dl)
  (mm:profile mm:profile-seal(list 35.0(- t0 10.0))1.0 1.0 0.0 dl)
  (mm:profile mm:profile-seal(list(- w 35.0)(- t0 10.0))-1.0 1.0 0.0 dl)))
 (if(= mode "I2")(setq result(mm:orient result w t0 nil T)))
 (mm2:colours result 250))
(defun mm2:layout (w t0 mode h side gap dl fl / x low high pivot r alpha fixed opened second specs hinge)
 (if(and(> w 200.0)(>= t0 70.0)(member h '(-1 1))(member side '(-1 1)))
  (progn
   (setq x(+ 30.0 gap)low(if(= mode "O2")(- t0 45.0)0.0)high(+ low 45.0)
    pivot(if(= side 1)high low)r(if *mm:double*(/(- w(* 2.0 x)gap)2.0)(- w(* 2.0 x)))
    alpha *mm:angle*)
   (if(and(> r 65.0)(> alpha 0.0)(<= alpha(/ pi 2.0)))
    (progn
     (setq fixed(append(mm:profile(mm2:closed r dl)(list x low)1.0 1.0 0.0 dl)
       (mm2:colours(mm:profile mm:profile-handle(list(+ x(- r 90.0))low)-1.0 -1.0 0.0 dl)250))
      opened(mm2:leaf x pivot r alpha side dl))
     (if *mm:double*(setq second(mm:orient(append fixed opened)w 0.0 T nil)))
     (setq specs(append(mm2:frame w t0 mode fl)(mm2:hardware w t0 mode dl)fixed opened second)
      hinge(list(if(= h 1)x(- w x))pivot))
     (list(mm:orient specs w 0.0(= h -1)nil)hinge
      (list(+ (car hinge)(* h r))pivot)
      (list(+ (car hinge)(* h r(cos alpha)))(+ pivot(* side r(sin alpha))))))))))



(defun mm:profile (items pos sx sy rot layer / result item pieces part)
 (foreach item items
  (setq pieces(mm:profile-v5(list item)pos sx sy rot layer))
  (if(nth 6 item)(setq pieces(mm2:colours pieces(nth 6 item))))
  (setq result(append result pieces)))result)
(defun mm:layout (w t0 mode h side leaf trim ret gap dl fl)
 (if(mm2:mode mode)(mm2:layout w t0 mode h side gap dl fl)
  (mm:layout-v5 w t0 mode h side leaf trim ret gap dl fl)))
(defun mm:spec-points (spec)(mm:spec-points-v5 spec))
(defun mm:emit (spec basis)(mm:emit-v5 spec basis))
(defun c:MM (/ *error* a b c got basis choice specs spec obj made good undo stop mm:newblock mm:building)
 (defun *error*(msg)
  (redraw)
  (if undo
   (progn(if made(entdel made))(mm:discard)(command-s "_.UNDO" "_End")))
  (if(and msg(not(wcmatch(strcase msg)"*CANCEL*,*QUIT*,*EXIT*,*取消*,*中断*")))
   (princ(strcat "\n" msg)))
  (princ))
 (may:prepare-many '("door" "door-frame" "opening"))
 (if(mm:settings)
 (if(> (abs(caddr(trans '(0.0 0.0 1.0)1 0 T)))0.999999)
  (progn
   (princ "\nMM：带套门：先内墙面、再外墙面、第三点定宽；鼠标只决定开向。")
   (while(not stop)
    (initget "I O N S I2 O2")
    (setq got(getpoint(strcat "\n"(cond((= *mm:mode* "I2")"内齐平2")((= *mm:mode* "O2")"外齐平2")((= *mm:mode* "I")"内齐平")((= *mm:mode* "O")"外齐平")((= *mm:mode* "S")"对开推拉门")((= *mm:mode* "L")"三扇联动门")(T"隐形门"))
       "：起点（带套门取内侧墙面）[内齐平(I)/外齐平(O)/内齐平2(I2)/外齐平2(O2)/隐形门(N)/设置(S)]：")))
    (cond
     ((= 'STR(type got))(if(= got "S")(mm:settings)(setq *mm:mode* got)))
     ((not got)(setq stop T))
     (T
      (setq a(trans got 1 0)b nil c nil basis nil choice nil)
      (setq got(getpoint got(if(mm:two *mm:mode*)"\n洞口另一端：""\n同一洞口边的外侧墙面点（量墙厚）：")))
      (if got(setq b(trans got 1 0)))
      (if(and b(not(mm:two *mm:mode*)))
       (if(setq got(getpoint(trans b 0 1)"\n沿墙拾取洞口另一端（定洞宽）："))(setq c(trans got 1 0))))
      (if b(setq basis(mm:basis a b c *mm:mode*)))
      (cond
       ((not basis)(princ "\n未生成；点位须同高，墙厚和洞宽不能为零。"))
       ((not(mm:layers-ok *mm:mode*))
        (princ "\n对应门图层缺失、关闭、冻结或锁定，请按S设置。"))
       ((not(mm:layout(nth 4 basis)(nth 3 basis)*mm:mode* 1 1 *mm:leaf* *mm:trim* *mm:return* *mm:gap* *mm:doorlayer* *mm:framelayer*))
        (princ "\n未生成；洞宽不足或墙厚小于门扇厚度加10mm。"))
       ((setq choice(mm:choose basis *mm:mode*))
        (setq *mm:mode*(cadr choice)specs(car(car choice))made nil good T)
        (command-s "_.UNDO" "_Begin")(setq undo T)
        (setq made(mm:insert specs basis *mm:mode*) good(if made T nil))
        (command-s "_.UNDO" "_End")(setq undo nil made nil)
        (if good(princ "\n门已生成。") (princ "\n生成失败，本次图元已移除。"))))))))
  (princ "\n当前UCS倾斜，请先切换到平面UCS。"))
 )
 (princ))
(princ)

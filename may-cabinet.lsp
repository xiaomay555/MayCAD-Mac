; MayCAD Mac portable public module.
(if (not *gz:depth*) (setq *gz:depth* 450.0))
(if (not *gz:type*) (setq *gz:type* "High"))
(if (not *gz:side*) (setq *gz:side* 1.0))
(defun gz:default-layer (kind)(may:layer(if(= kind "Low")"cabinet-low""cabinet-high")))
(if (not *gz:layer*) (setq *gz:layer* (gz:default-layer *gz:type*)))
(defun gz:layer-ok (name / r)
 (and (setq r(tblsearch "LAYER" name)) (> (cdr(assoc 62 r)) 0)
  (= 0 (logand 5 (cdr(assoc 70 r))))))
(defun gz:layers (/ r result)
 (setq r(tblnext "LAYER" T))
 (while r
  (if (and (= 0 (logand 16 (cdr(assoc 70 r)))) (not(wcmatch(cdr(assoc 2 r)) "*|*")))
   (setq result(cons(cdr(assoc 2 r)) result)))
  (setq r(tblnext "LAYER")))
 (acad_strlsort result))
(defun gz:ui-accept (/ dep lay idx)
 (setq dep(distof(get_tile "depth")2) gz:ui-type(if(= (get_tile "kind")"1")"Low""High") idx(atoi(get_tile "layer")))
 (setq lay(if(= idx 0)(gz:default-layer gz:ui-type)(nth(1- idx) gz:ui-layers)))
 (cond
  ((or (not dep)(<= dep 40.0)) (set_tile "error" "柜深须大于40mm。"))
  ((not(gz:layer-ok lay)) (set_tile "error" "请选本图中已开启、解冻且未锁定的图层。"))
  (T (setq *gz:depth* dep *gz:type* gz:ui-type *gz:layer* lay) (done_dialog 1))))
(defun gz:settings (/ id status idx src dst line temp layer-list)
 (setq gz:ui-layers(gz:layers) gz:ui-type *gz:type*)
 (setq idx(vl-position *gz:layer* gz:ui-layers))
 (setq idx(if(and idx(/= *gz:layer*(gz:default-layer *gz:type*)))(1+ idx)0))
 (setq temp (may:temp-ui "gzz"))
 (setq layer-list "")
 (foreach line gz:ui-layers (setq layer-list(strcat layer-list (if(= layer-list "")"""\\n") line)))
 (setq src(open (may:resource "may-cabinet.dcl") "r" "utf8") dst(open temp "w" "utf8"))
 (while(setq line(read-line src))
  (setq line(vl-string-subst(rtos *gz:depth* 2 0)"$DEPTH$" line))
  (setq line(vl-string-subst(if(= *gz:type* "Low")"1""0")"$KIND$" line))
  (setq line(vl-string-subst(itoa(if idx idx 0))"$LAYER$" line))
  (setq line(vl-string-subst layer-list "$LAYERS$" line))
  (write-line line dst))
 (close src)(close dst)
 (setq id(load_dialog temp))
 (if (and (> id 0)(new_dialog "may_cabinet" id))
  (progn
   (action_tile "accept" "(gz:ui-accept)")
   (action_tile "cancel" "(done_dialog 0)")
   (mode_tile "depth" 2)
   (setq status(start_dialog))))
 (if (and id (> id 0)) (unload_dialog id))
 (= status 1))
(defun gz:poly (pts closed color) (list pts closed color))
(defun gz:line (p q) (gz:poly(list p q)nil 251))
(defun gz:geometry (len dep kind / specs n step i x0 x1)
 (if (and (> len 40.0)(> dep 40.0)(member kind '("High" "Low")))
  (progn
   (setq specs(list
    (gz:poly(list '(0.0 0.0)(list len 0.0)(list len dep)(list 0.0 dep))T nil)
    (gz:poly(list '(20.0 20.0)(list(- len 20.0)20.0)(list(- len 20.0)(- dep 20.0))(list 20.0(- dep 20.0)))T 251)))
   (setq n(max 1(fix(/ (+ len 799.999999)800.0))) step(/ (- len 40.0)n) i 0)
   (repeat n
    (setq x0(+ 20.0(* i step)) x1(+ x0 step))
    (setq specs(append specs(list(gz:line(list x0 20.0)(list x1(- dep 20.0))))))
    (if (= kind "High") (setq specs(append specs(list(gz:line(list x0(- dep 20.0))(list x1 20.0))))))
    (if (> i 0) (setq specs(append specs(list(gz:line(list x0 20.0)(list x0(- dep 20.0)))))))
    (setq i(1+ i)))
   specs)))
(defun gz:emit (spec layer / d)
 (setq d(append
  (list '(0 . "LWPOLYLINE")'(100 . "AcDbEntity")(cons 8 layer))
  (if(caddr spec)(list(cons 62(caddr spec)))nil)
  (list '(100 . "AcDbPolyline")(cons 90(length(car spec)))(cons 70(if(cadr spec)1 0)))
  (mapcar '(lambda(p)(cons 10 p))(car spec))))
 (entmake d))
(defun gz:make (p q dep kind layer side / len specs name n good e ang)
 (cond
  ((not(gz:layer-ok layer))(princ "\n目标图层不存在、关闭、冻结或锁定，本次未生成。")nil)
  ((or (not p)(not q)(not(equal(caddr p)(caddr q)1e-6)))(princ "\n两点须在同一水平面。")nil)
  ((not(member side '(-1.0 1.0)))(princ "\n柜体方向无效。")nil)
  (T
   (setq len(distance(list(car p)(cadr p))(list(car q)(cadr q))) specs(gz:geometry len dep kind))
   (if specs
    (progn
     (setq n 1 name "GZZ_1")
     (while(tblsearch "BLOCK" name)(setq n(1+ n) name(strcat "GZZ_"(itoa n))))
     (setq good(entmake(list '(0 . "BLOCK")(cons 8 layer)(cons 2 name)'(70 . 0)'(10 0.0 0.0 0.0))))
     (foreach e specs (if good(setq good(gz:emit e layer))))
     (if good(setq good(entmake '((0 . "ENDBLK")))))
     (if good(setq good(entmake(list '(0 . "INSERT")(cons 8 layer)(cons 2 name)(cons 10 p)'(41 . 1.0)(cons 42 side)'(43 . 1.0)(cons 50(angle p q))))))
     (if good(entlast)(princ "\n生成失败，请撤销本次绘制。")))
    (progn(princ "\n柜长和柜深须大于40mm，本次未生成。")nil)))))
(defun gz:option (key / d)
 (cond
  ((= key "S")(gz:settings))
  ((= key "F")(setq *gz:side* (- *gz:side*)) (princ "\n已反向。") T)
  ((= key "D")(initget 6)(setq d(getreal(strcat "\n柜深 <"(rtos *gz:depth* 2 0)">：")))
   (if d (if (> d 40.0)(setq *gz:depth* d)(princ "\n柜深须大于40mm。"))) T)
  ((member key '("G" "B"))(setq *gz:type*(if(= key "G")"High""Low") *gz:layer*(gz:default-layer *gz:type*)) T)))
(defun c:GZZ (/ *error* p q got stop undo made)
 (defun *error* (msg)
  (if undo(command-s "_.UNDO" "_End"))
  (if(and msg(not(wcmatch(strcase msg)"*CANCEL*,*QUIT*,*EXIT*,*取消*,*中断*")))(princ(strcat "\n" msg)))
  (princ))
 (may:prepare-many '("cabinet-high" "cabinet-low"))
 (if(gz:settings)
  (progn
   (princ "\n点柜体背边两端生成，可连续画；F反向，S设置，D柜深，G高柜，B半高柜，空格结束。")
   (while(not stop)
    (initget "S F D G B")
    (setq got(getpoint "\n柜子起点 [设置(S)/反向(F)/柜深(D)/高柜(G)/半高柜(B)]："))
    (cond
     ((= 'STR(type got))(gz:option got))
     ((not got)(setq stop T))
     (T
      (setq p(trans got 1 0) q nil)
      (while(and(not q)(not stop))
       (initget "S F D G B")
       (setq got(getpoint(trans p 0 1)"\n柜子终点 [设置(S)/反向(F)/柜深(D)/高柜(G)/半高柜(B)]："))
       (cond
        ((= 'STR(type got))(gz:option got))
        ((not got)(setq stop T))
        (T(setq q(trans got 1 0)))))
      (if q
       (progn
        (command-s "_.UNDO" "_Begin")(setq undo T)
        (setq made(gz:make p q *gz:depth* *gz:type* *gz:layer* *gz:side*))
        (command-s "_.UNDO" "_End")(setq undo nil)
        (if made(princ "\n柜子完成。")))))))))
 (princ))
(princ)

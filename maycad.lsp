; Loaded after installing into the user-owned MayCAD application support folder.
(if(not may:root)(setq may:root(strcat(getenv "HOME")"/Library/Application Support/MayCAD/")))
(load(strcat may:root "maycad-core.lsp"))
(load(may:resource "may-xline.lsp"))
(load(may:resource "tt.lsp"))
(load(may:resource "ty.lsp"))
(load(may:resource "may-arrange.lsp"))
(load(may:resource "may-draworder.lsp"))
(load(may:resource "may-wardrobe.lsp"))
(load(may:resource "may-cabinet.lsp"))
(load(may:resource "may-curtain.lsp"))
(load(may:resource "may-led.lsp"))
(load(may:resource "may-door.lsp"))
(load(may:resource "may-layer-isolate.lsp"))
(load(may:resource "may-qp.lsp"))
(load(may:resource "may-window.lsp"))
(may:sync)
(c:MAYINFO)
(princ)

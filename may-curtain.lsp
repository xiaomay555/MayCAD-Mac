; MayCAD Mac portable public module.
(if(not *cl:count*)(setq *cl:count* 1))
(if(not *cl:thick*)(setq *cl:thick* 80.0))
(if(not *cl:offset*)(setq *cl:offset* 100.0))
(if(not *cl:gap*)(setq *cl:gap* 100.0))
(if(not *cl:side*)(setq *cl:side* 1.0))
(if(not *cl:curtainlayer*)(setq *cl:curtainlayer* (may:layer "curtain")))
(defun cl:layer-ok (name / r)
 (and (setq r(tblsearch "LAYER" name)) (> (cdr(assoc 62 r))0)
  (= 0(logand 5(cdr(assoc 70 r))))))
(defun cl:layers (/ r result)
 (setq r(tblnext "LAYER" T))
 (while r
  (if(and (= 0(logand 16(cdr(assoc 70 r))))(not(wcmatch(cdr(assoc 2 r))"*|*")))
   (setq result(cons(cdr(assoc 2 r))result)))
  (setq r(tblnext "LAYER")))
 (acad_strlsort result))
(defun cl:valid (thick offset gap count)
 (cond
  ((or(not thick)(< thick 10.0)) "每层厚度不能小于10mm。")
  ((or(not offset)(< offset(/ thick 2.0))) "离墙距离不能小于窗帘厚度的一半。")
  ((or(not gap)(< gap 0.0)) "双层间距不能为负。")
  ((and (= count 2)(< gap thick)) "双层中心间距不能小于每层厚度。")
  (T nil)))
(defun cl:accept (/ th off gap count cur err)
 (setq th(distof(get_tile "thick")2) off(distof(get_tile "offset")2)
  gap(distof(get_tile "gap")2) count(1+(atoi(get_tile "count")))
  cur(nth(atoi(get_tile "curtainlayer"))cl:ui-layers)
  err(cl:valid th off gap count))
 (cond
  (err(set_tile "error" err))
  ((not(cl:layer-ok cur))(set_tile "error" "窗帘图层须存在、开启、解冻且未锁定。"))
  (T
   (setq *cl:thick* th *cl:offset* off *cl:gap* gap *cl:count* count
    *cl:curtainlayer* cur)
   (done_dialog 1))))
(defun cl:settings (/ src dst line temp id result names ci replacements pair)
 (setq cl:ui-layers(cl:layers) ci(vl-position *cl:curtainlayer* cl:ui-layers)
  names "")
 (foreach line cl:ui-layers (setq names(strcat names(if(= names "")"""\\n")line)))
 (setq replacements(list
  (cons "$COUNT$"(itoa(1- *cl:count*)))
  (cons "$THICK$"(rtos *cl:thick* 2 2)) (cons "$OFFSET$"(rtos *cl:offset* 2 2))
  (cons "$GAP$"(rtos *cl:gap* 2 2)) (cons "$LAYERS$" names)
  (cons "$CURTAINLAYER$"(itoa(if ci ci 0)))))
 (setq temp (may:temp-ui "clpm")
  src(open (may:resource "may-curtain.dcl") "r" "utf8")
  dst(open temp "w" "utf8"))
 (while(setq line(read-line src))
  (foreach pair replacements(setq line(vl-string-subst(cdr pair)(car pair)line)))
  (write-line line dst))
 (close src)(close dst)
 (setq id(load_dialog temp))
 (if(and (> id 0)(new_dialog "may_curtain" id))
  (progn
   (action_tile "accept" "(cl:accept)") (action_tile "cancel" "(done_dialog 0)")
   (setq result(start_dialog))))
 (if(and id(> id 0))(unload_dialog id))
 (= result 1))
(defun cl:wave (len thick offset / n a step radius margin b i result)
 (if(and (>= len thick)(>= thick 10.0))
  (progn
   (setq n(max 2(* 2(fix(+ 0.5(/ len(* thick 1.25)))))))
   (setq a(* thick(1- n)))
   (setq step(/ (-(* 2.0 thick len)(* thick thick))
    (+ (sqrt(+(* a a)(* 2.0 thick len)(-(* thick thick)))) a)))
   (setq b(/ thick step) radius(/(+(* step step)(* thick thick))(* 4.0 thick))
    margin(- radius(/ step 2.0)) i 0)
   (repeat(1+ n)
    (setq result(cons(list(+ margin(* i step))offset(if(= i n)0.0(if(= 0(rem i 2))b(- b))))result))
    (setq i(1+ i)))
   (reverse result))))
(defun cl:emit (verts p u side layer light / data v q x y)
 (setq v(list(* side(- (cadr u)))(* side(car u))))
 (setq data(append(list '(0 . "LWPOLYLINE")'(100 . "AcDbEntity")(cons 8 layer))
  (if light '((6 . "M-DASHDOT"))nil)
  (list '(100 . "AcDbPolyline")(cons 90(length verts))'(70 . 0)(cons 38(caddr p)))))
 (foreach q verts
  (setq x(+ (car p)(* (car q)(car u))(* (cadr q)(car v)))
   y(+ (cadr p)(* (car q)(cadr u))(* (cadr q)(cadr v))))
  (setq data(append data(list(cons 10(list x y))(cons 42(* side(caddr q)))))))
 (if(entmake data)(entlast)))
(defun cl:make (p q count thick offset gap cur side / len u specs verts records good obj)
 (cond
  ((or(not p)(not q)(not(equal(caddr p)(caddr q)1e-6)))
   (princ "\n两点须在同一水平面，本次未生成。")nil)
  ((or(not(member count '(1 2)))(not(member side '(-1.0 1.0)))(cl:valid thick offset gap count))
   (princ "\n窗帘参数无效，本次未生成。")nil)
  ((not(cl:layer-ok cur))
   (princ "\n目标图层不存在、关闭、冻结或锁定，本次未生成。")nil)
  (T
   (setq len(distance(list(car p)(cadr p))(list(car q)(cadr q))))
   (if(< len thick) (progn(princ "\n长度不能小于每层厚度，本次未生成。")nil)
    (progn
     (setq u(list(/(- (car q)(car p))len)(/(- (cadr q)(cadr p))len)))
     (setq specs(list(cl:wave len thick offset)))
     (if(= count 2)(setq specs(append specs(list(cl:wave len thick(+ offset gap))))))
     (setq good T)
     (foreach verts specs
      (if good
       (if(setq obj(cl:emit verts p u side cur nil))(setq records(cons obj records))(setq good nil))))
     (if good(reverse records)
      (progn(foreach obj records(entdel obj))(princ "\n生成失败，已移除本次生成的曲线。")nil)))))))
(defun c:CLPM (/ *error* p q got stop undo result)
 (defun *error* (msg)
  (if undo(command-s "_.UNDO" "_End"))
  (if(and msg(not(wcmatch(strcase msg)"*CANCEL*,*QUIT*,*EXIT*,*取消*,*中断*")))(princ(strcat "\n" msg)))
  (princ))
 (may:prepare "curtain")
 (if(cl:settings)
  (progn
   (princ "\n点墙边基线两端画窗帘，可连续绘制；F反向、S设置，空格结束。")
   (while(not stop)
    (initget "S F")
    (setq got(getpoint "\n墙边基线起点 [设置(S)/反向(F)]："))
    (cond
     ((and(= 'STR(type got))(= got "S"))(cl:settings))
     ((and(= 'STR(type got))(= got "F"))(setq *cl:side*(- *cl:side*)) (princ "\n已反向。"))
     ((not got)(setq stop T))
     (T
      (setq p(trans got 1 0) q nil)
      (while(and(not q)(not stop))
       (initget "S F")
       (setq got(getpoint(trans p 0 1)"\n墙边基线终点 [设置(S)/反向(F)]："))
       (cond
        ((and(= 'STR(type got))(= got "S"))(cl:settings))
        ((and(= 'STR(type got))(= got "F"))(setq *cl:side*(- *cl:side*)) (princ "\n已反向。"))
        ((not got)(setq stop T))
        (T(setq q(trans got 1 0)))))
      (if q
       (progn
        (command-s "_.UNDO" "_Begin")(setq undo T)
        (setq result(cl:make p q *cl:count* *cl:thick* *cl:offset* *cl:gap* *cl:curtainlayer* *cl:side*))
        (command-s "_.UNDO" "_End")(setq undo nil)
        (if result(princ "\n窗帘完成。")))))))))
 (princ))
(princ)

; MayCAD Mac portable public module.
(defun may:az (v) (if v v 0.0))
(defun may:av (d k v) (if (assoc k d) (cdr (assoc k d)) v))
(defun may:plus (a b) (mapcar '+ a b))
(defun may:minus (a b) (mapcar '- a b))
(defun may:times (a s) (mapcar '(lambda (x) (* x s)) a))
(defun may:dot (a b) (+ (* (car a) (car b)) (* (cadr a) (cadr b))))
(defun may:point (m p) (list (+ (* (nth 0 m) (car p)) (* (nth 1 m) (cadr p)) (nth 4 m)) (+ (* (nth 2 m) (car p)) (* (nth 3 m) (cadr p)) (nth 5 m))))
(defun may:vector (m p) (list (+ (* (nth 0 m) (car p)) (* (nth 1 m) (cadr p))) (+ (* (nth 2 m) (car p)) (* (nth 3 m) (cadr p)))))
(defun may:matrix (m n / a b c d x y)
 (setq a (nth 0 m) b (nth 1 m) c (nth 2 m) d (nth 3 m) x (nth 4 m) y (nth 5 m))
 (list (+ (* a (nth 0 n)) (* b (nth 2 n))) (+ (* a (nth 1 n)) (* b (nth 3 n))) (+ (* c (nth 0 n)) (* d (nth 2 n))) (+ (* c (nth 1 n)) (* d (nth 3 n))) (+ (* a (nth 4 n)) (* b (nth 5 n)) x) (+ (* c (nth 4 n)) (* d (nth 5 n)) y)))
(defun may:bbadd (p)
 (if may:bounds (setq may:bounds (list (mapcar 'min (car may:bounds) p) (mapcar 'max (cadr may:bounds) p))) (setq may:bounds (list p p))))
(defun may:bbpoint (m p) (may:bbadd (may:point m p)))
(defun may:anglemod (a) (while (< a 0.0) (setq a (+ a (* 2.0 pi)))) (rem a (* 2.0 pi)))
(defun may:inarc (a s sweep) (if (< sweep 0.0) (<= (may:anglemod (- s a)) (+ (- sweep) 1e-9)) (<= (may:anglemod (- a s)) (+ sweep 1e-9))))
(defun may:bbarc (m c u v s sweep / tc tu tv angles a)
 (setq tc (may:point m c) tu (may:vector m u) tv (may:vector m v))
 (setq angles (list s (+ s sweep) (atan (car tv) (car tu)) (+ pi (atan (car tv) (car tu))) (atan (cadr tv) (cadr tu)) (+ pi (atan (cadr tv) (cadr tu)))))
 (foreach a angles (if (may:inarc a s sweep) (may:bbadd (may:plus tc (may:plus (may:times tu (cos a)) (may:times tv (sin a))))))))
(defun may:bulge (m p q b / v len mid c r a sweep)
 (if (< (abs b) 1e-12) (progn (may:bbpoint m p) (may:bbpoint m q))
 (progn (setq v (may:minus q p) len (distance p q))
  (if (> len 1e-12) (progn
   (setq mid (may:times (may:plus p q) 0.5) c (may:plus mid (may:times (list (- (cadr v)) (car v)) (/ (- 1.0 (* b b)) (* 4.0 b)))))
   (setq r (distance p c) a (angle c p) sweep (* 4.0 (atan b)))
   (may:bbarc m c (list r 0.0) (list 0.0 r) a sweep))
   (may:bbpoint m p)))))
(defun may:lwverts (d / out p b item)
 (setq b 0.0)
 (foreach item d (cond ((= 10 (car item)) (if p (setq out (cons (list p b) out))) (setq p (list (cadr item) (caddr item)) b 0.0)) ((= 42 (car item)) (setq b (cdr item)))))
 (if p (setq out (cons (list p b) out))) (reverse out))
(defun may:polybb (m verts closed / rest a b)
 (setq rest verts)
 (while (cdr rest) (setq a (car rest) b (cadr rest)) (may:bulge m (car a) (car b) (cadr a)) (setq rest (cdr rest)))
 (if (and closed verts) (may:bulge m (caar rest) (caar verts) (cadar rest)))
 (if (= 1 (length verts)) (may:bbpoint m (caar verts))))
(defun may:planar (d) (equal (may:av d 210 '(0.0 0.0 1.0)) '(0.0 0.0 1.0) 1e-8))
(defun may:bad (typ) (if (not may:badtype) (setq may:badtype typ)))
(defun may:textbb (d m / box ins ang n p)
 (if (setq box (textbox d))
 (progn (setq ins (may:av d 10 '(0.0 0.0 0.0)) ang (may:av d 50 0.0))
  (setq n (may:matrix m (list (cos ang) (- (sin ang)) (sin ang) (cos ang) (car ins) (cadr ins))))
  (foreach p (list (car box) (cadr box) (list (caar box) (cadadr box)) (list (caadr box) (cadar box))) (may:bbpoint n p)))
 (may:bad "TEXT")))
(defun may:blockbb (name m depth / rec e d flags)
 (if (or (> depth 24) (not (setq rec (tblsearch "BLOCK" name))) (/= 0 (logand (may:av rec 70 0) 12))) (may:bad "XREF/BLOCK")
 (progn (setq e (cdr (assoc -2 rec)))
 (while (and e (/= "ENDBLK" (cdr (assoc 0 (entget e))))) (may:entitybb e m (1+ depth)) (setq e (entnext e))))))
(defun may:hatchbb (d m / n item flags count verts p b edge c r a z u ratio sweep rest)
 (setq rest (member (assoc 91 d) d))
 (if rest (setq rest (cdr rest)))
 (while (and rest (not may:badtype))
  (if (= 92 (caar rest))
   (progn (setq flags (cdar rest) rest (cdr rest))
    (if (/= 0 (logand flags 2))
     (progn
      (while (and rest (/= 93 (caar rest))) (setq rest (cdr rest)))
      (setq count (cdar rest) rest (cdr rest) verts nil)
      (repeat count
       (if (/= 10 (caar rest)) (may:bad "HATCH")
        (progn (setq p (list (cadar rest) (caddar rest)) rest (cdr rest) b 0.0)
         (if (= 42 (caar rest)) (setq b (cdar rest) rest (cdr rest)))
         (setq verts (cons (list p b) verts)))))
      (if (not may:badtype) (may:polybb m (reverse verts) T)))
     (progn
      (while (and rest (/= 93 (caar rest))) (setq rest (cdr rest)))
      (setq count (cdar rest) rest (cdr rest))
      (repeat count
       (setq edge (cdar rest) rest (cdr rest))
       (cond
        ((= edge 1) (may:bbpoint m (cdar rest)) (setq rest (cdr rest)) (may:bbpoint m (cdar rest)) (setq rest (cdr rest)))
        ((= edge 2)
         (setq c (cdar rest) r (cdadr rest) a (* pi (/ (cdaddr rest) 180.0)) z (* pi (/ (cdr (nth 3 rest)) 180.0)))
         (setq sweep (if (= 1 (cdr (nth 4 rest))) (may:anglemod (- z a)) (- (may:anglemod (- a z)))))
         (if (< (abs sweep) 1e-9) (setq sweep (if (= 1 (cdr (nth 4 rest))) (* 2.0 pi) (* -2.0 pi))))
         (may:bbarc m c (list r 0.0) (list 0.0 r) a sweep) (setq rest (nthcdr 5 rest)))
        (T (may:bad "HATCH-EDGE") (setq rest nil count 0)))))))
   (setq rest (cdr rest))))
 (if (not (assoc 91 d)) (may:bad "HATCH")))
(defun may:entitybb (e m depth / d typ p q r a b s sx sy n rec base verts v item next width txt ins w h ang att u)
 (setq d (entget e) typ (cdr (assoc 0 d)))
 (if (and d (or (not (= typ "ATTRIB")) (= 0 (logand 1 (may:av d 70 0)))))
 (if (not (may:planar d)) (may:bad "NON-PLANAR")
 (cond
  ((= typ "LINE") (may:bbpoint m (cdr (assoc 10 d))) (may:bbpoint m (cdr (assoc 11 d))))
  ((= typ "POINT") (may:bbpoint m (cdr (assoc 10 d))))
  ((member typ '("CIRCLE" "ARC"))
   (setq p (cdr (assoc 10 d)) r (cdr (assoc 40 d)) a (if (= typ "ARC") (cdr (assoc 50 d)) 0.0) s (if (= typ "ARC") (may:anglemod (- (cdr (assoc 51 d)) a)) (* 2.0 pi)))
   (may:bbarc m p (list r 0.0) (list 0.0 r) a s))
  ((= typ "ELLIPSE")
   (setq p (cdr (assoc 10 d)) u (cdr (assoc 11 d)) r (cdr (assoc 40 d)) a (cdr (assoc 41 d)) s (- (cdr (assoc 42 d)) a))
   (if (< s 0.0) (setq s (+ s (* 2.0 pi))))
   (may:bbarc m p u (list (* (- (cadr u)) r) (* (car u) r)) a s))
  ((= typ "LWPOLYLINE")
   (if (or (> (abs (may:av d 43 0.0)) 1e-9) (vl-some '(lambda (x) (and (member (car x) '(40 41)) (> (abs (cdr x)) 1e-9))) d)) (may:bad "WIDE-POLYLINE")
    (may:polybb m (may:lwverts d) (/= 0 (logand 1 (may:av d 70 0))))))
  ((= typ "POLYLINE")
   (if (/= 0 (logand (may:av d 70 0) 80)) (may:bad "MESH")
    (progn (setq next (entnext e) verts nil)
     (while (and next (= "VERTEX" (cdr (assoc 0 (setq v (entget next))))))
      (if (or (> (abs (may:av v 40 (may:av d 40 0.0))) 1e-9) (> (abs (may:av v 41 (may:av d 41 0.0))) 1e-9)) (may:bad "WIDE-POLYLINE"))
      (setq verts (cons (list (cdr (assoc 10 v)) (may:av v 42 0.0)) verts) next (entnext next)))
     (may:polybb m (reverse verts) (/= 0 (logand 1 (may:av d 70 0)))))))
  ((= typ "INSERT")
   (if (or (> (may:av d 70 1) 1) (> (may:av d 71 1) 1)) (may:bad "MINSERT")
    (progn
     (setq p (cdr (assoc 10 d)) a (may:av d 50 0.0) sx (may:av d 41 1.0) sy (may:av d 42 1.0) rec (tblsearch "BLOCK" (cdr (assoc 2 d))) base (may:av rec 10 '(0.0 0.0 0.0)))
     (setq n (list (* sx (cos a)) (* (- sy) (sin a)) (* sx (sin a)) (* sy (cos a)) 0.0 0.0))
     (setq q (may:vector n base) n (append (list (nth 0 n) (nth 1 n) (nth 2 n) (nth 3 n)) (list (- (car p) (car q)) (- (cadr p) (cadr q)))))
     (may:blockbb (cdr (assoc 2 d)) (may:matrix m n) depth)
     (if (= 1 (may:av d 66 0))
      (progn (setq next (entnext e))
       (while (and next (= "ATTRIB" (cdr (assoc 0 (entget next))))) (may:entitybb next m depth) (setq next (entnext next))))))))
  ((member typ '("TEXT" "ATTRIB")) (may:textbb d m))
  ((= typ "ATTDEF") nil)
  ((= typ "MTEXT")
   (setq w (may:av d 42 0.0) h (may:av d 43 0.0) ins (cdr (assoc 10 d)) u (may:av d 11 '(1.0 0.0 0.0)) att (may:av d 71 1))
   (if (or (<= w 0.0) (<= h 0.0)) (may:bad "MTEXT-EXTENTS")
    (progn (setq a (atan (cadr u) (car u)) n (may:matrix m (list (cos a) (- (sin a)) (sin a) (cos a) (car ins) (cadr ins))))
     (setq p (list (* w (/ (- (rem (1- att) 3)) 2.0)) (* h (/ (fix (/ (1- att) 3)) 2.0))))
     (foreach q (list p (may:plus p (list w 0.0)) (may:plus p (list 0.0 (- h))) (may:plus p (list w (- h)))) (may:bbpoint n q)))))
  ((member typ '("SOLID" "TRACE" "3DFACE")) (foreach item d (if (member (car item) '(10 11 12 13)) (may:bbpoint m (cdr item)))))
  ((= typ "HATCH") (may:hatchbb d m))
  ((= typ "DIMENSION") (if (assoc 2 d) (may:blockbb (cdr (assoc 2 d)) m depth) (may:bad typ)))
  ((member typ '("VERTEX" "SEQEND" "ENDBLK")) nil)
  (T (may:bad typ))))))
(defun may:bb (ss basis / may:bounds may:badtype i)
 (setq i 0)
 (repeat (sslength ss) (may:entitybb (ssname ss i) basis 0) (setq i (1+ i)))
 (if may:badtype (progn (princ (strcat "\n暂不处理此对象类型：" may:badtype "。本次未移动。")) nil) may:bounds))
(defun may:singlebb (e basis / ss) (setq ss (ssadd)) (ssadd e ss) (may:bb ss basis))
(defun may:mid (bb) (may:times (may:plus (car bb) (cadr bb)) 0.5))
(defun may:locked (ss / i locked d)
 (setq i 0)
 (repeat (sslength ss) (setq d (tblsearch "LAYER" (cdr (assoc 8 (entget (ssname ss i)))))) (if (/= 0 (logand 4 (cdr (assoc 70 d)))) (setq locked T)) (setq i (1+ i))) locked)
(defun may:move (ss delta) (command-s "_.MOVE" ss "" "_non" '(0.0 0.0 0.0) "_non" (trans (list (car delta) (cadr delta) 0.0) 0 1 T)))
(defun may:rect (e / d v p q r s a b tol)
 (setq d (entget e))
 (if (and (= "LWPOLYLINE" (cdr (assoc 0 d))) (may:planar d) (/= 0 (logand 1 (may:av d 70 0))) (= 4 (length (setq v (may:lwverts d)))) (not (vl-some '(lambda (x) (> (abs (cadr x)) 1e-9)) v)))
  (progn
   (setq p (caar v) q (caadr v) r (car (nth 2 v)) s (car (nth 3 v)) a (may:minus q p) b (may:minus s p) tol (* (distance p q) (distance p s)))
   (if (and (> tol 1e-9) (< (abs (may:dot a b)) (* tol 1e-8)) (equal (may:plus p r) (may:plus q s) 1e-6)) (list (may:times (may:plus p r) 0.5) (may:times a (/ 1.0 (distance p q))) (may:times b (/ 1.0 (distance p s))))))))
(defun may:center (ss boundary / frame u v basis bb center target delta)
 (cond ((may:locked ss) (princ "\n所选对象有锁定图层，请先解锁。") nil)
 ((not (setq frame (may:rect boundary))) (princ "\n请选择闭合矩形多段线边框。") nil)
 ((ssmemb boundary ss) (princ "\n边框不能同时作为待居中对象。") nil)
 (T (setq u (cadr frame) v (caddr frame) basis (list (car u) (cadr u) (car v) (cadr v) 0.0 0.0))
  (if (setq bb (may:bb ss basis))
   (progn (setq center (may:mid bb) target (may:point basis (car frame)) delta (may:minus target center))
    (may:move ss (may:plus (may:times u (car delta)) (may:times v (cadr delta)))) T)))))
(defun c:ZZZ (/ *error* ss picked undo)
 (defun *error* (msg) (if undo (command-s "_.UNDO" "_End")) (if (not (wcmatch (strcase msg) "*CANCEL*,*QUIT*,*EXIT*,*取消*,*中断*")) (princ (strcat "\n" msg))) (princ))
 (princ "\n选择要整体居中的对象：")
 (if (setq ss (ssget)) (if (setq picked (entsel "\n选择矩形边框：")) (progn (command-s "_.UNDO" "_Begin") (setq undo T) (may:center ss (car picked)) (command-s "_.UNDO" "_End") (setq undo nil)))) (princ))
(defun may:distribute (ss p1 p2 / u v basis span items i e bb center len total item gap pos target delta one result)
 (setq span (distance p1 p2))
 (cond ((< (sslength ss) 2) (princ "\n至少选择两个对象；每个块或独立图元算一件。") nil)
 ((may:locked ss) (princ "\n所选对象有锁定图层，请先解锁。") nil)
 ((not (equal (may:az (caddr p1)) (may:az (caddr p2)) 1e-7)) (princ "\n请选择同一水平面上的两个点。") nil)
 ((< span 1e-8) (princ "\n起点和终点不能重合。") nil)
 (T
  (setq u (may:times (may:minus p2 p1) (/ 1.0 span)) v (list (- (cadr u)) (car u)) basis (list (car u) (cadr u) (car v) (cadr v) 0.0 0.0) i 0 total 0.0 result T)
  (repeat (sslength ss)
   (setq e (ssname ss i) bb (may:singlebb e basis))
   (if bb (progn (setq len (- (caadr bb) (caar bb)) center (may:mid bb) total (+ total len)) (setq items (cons (list e center len i) items))) (setq result nil))
   (setq i (1+ i)))
  (cond ((not result) nil)
   ((< (- span total) -1e-6) (princ "\n这段长度放不下所选物体，本次未移动。") nil)
   (T
    (setq items (vl-sort items '(lambda (a b) (if (equal (caadr a) (caadr b) 1e-8) (< (nth 3 a) (nth 3 b)) (< (caadr a) (caadr b))))))
    (setq gap (/ (- span total) (1- (length items))) pos (may:dot u p1))
    (foreach item items
     (setq len (nth 2 item) target (list (+ pos (/ len 2.0)) (may:dot v p1)) delta (may:minus target (cadr item)) one (ssadd))
     (ssadd (car item) one) (may:move one (may:plus (may:times u (car delta)) (may:times v (cadr delta))))
     (setq pos (+ pos len gap))) T)))))
(defun c:FF (/ *error* ss p1 p2 undo)
 (defun *error* (msg) (if undo (command-s "_.UNDO" "_End")) (if (not (wcmatch (strcase msg) "*CANCEL*,*QUIT*,*EXIT*,*取消*,*中断*")) (princ (strcat "\n" msg))) (princ))
 (princ "\n选择要等间隙排列的对象（多线家具先成块）：")
 (if (setq ss (ssget)) (if (setq p1 (getpoint "\n指定排列范围的外侧起点：")) (if (setq p2 (getpoint p1 "\n指定排列范围的外侧终点："))
  (progn (command-s "_.UNDO" "_Begin") (setq undo T) (may:distribute ss (trans p1 1 0) (trans p2 1 0)) (command-s "_.UNDO" "_End") (setq undo nil))))) (princ))
(princ)

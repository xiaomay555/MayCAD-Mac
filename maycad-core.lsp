; MayCAD portable runtime. No personal template or project geometry is included.
(setq may:version "0.1.0-preview")
(if(not may:root)(setq may:root(strcat(getenv "HOME")"/Library/Application Support/MayCAD/")))
(setq may:cache(strcat(getenv "HOME")"/Library/Caches/MayCAD/")
      may:user(strcat(getenv "HOME")"/Library/Application Support/MayCADUser/"))
(defun may:mkdir (path / parent)
 (or(vl-file-directory-p path)
  (and(setq parent(vl-filename-directory path))(/= parent path)
   (may:mkdir parent)(vl-mkdir path))))
(may:mkdir may:cache)
(defun may:resource (name)(strcat may:root name))
(defun may:temp-ui (name)(vl-filename-mktemp(strcat "maycad-" name "-")may:cache ".dcl"))
(if(not may:layers)
 (setq may:layers '(("wardrobe" . "MayCAD-Wardrobe")("cabinet-high" . "MayCAD-Cabinet-High")
  ("cabinet-low" . "MayCAD-Cabinet-Low")("curtain" . "MayCAD-Curtain")
  ("led" . "MayCAD-LED")("door" . "MayCAD-Door")("door-frame" . "MayCAD-Door-Frame")
  ("opening" . "MayCAD-Opening")("window" . "MayCAD-Window"))))
(defun may:layer (role)(cdr(assoc role may:layers)))
(defun may:layer-ok (name / row)
 (and name(setq row(tblsearch "LAYER" name))(> (cdr(assoc 62 row))0)
  (= 0(logand 21(cdr(assoc 70 row))))))
(defun may:prepare (role / name)
 (setq name(may:layer role))
 (if(and name(not(tblsearch "LAYER" name)))
  (entmake(list '(0 . "LAYER")'(100 . "AcDbSymbolTableRecord")'(100 . "AcDbLayerTableRecord")
   (cons 2 name)'(70 . 0)'(62 . 7)'(6 . "Continuous")'(290 . 1)'(370 . -3))))
 (may:layer-ok name))
(defun may:prepare-many (roles / ok role)
 (setq ok T)(foreach role roles(if(not(may:prepare role))(setq ok nil)))ok)
(defun may:sync ()
 (setq *gz:layer*(may:layer(if(= *gz:type* "Low")"cabinet-low""cabinet-high"))
  *cl:curtainlayer*(may:layer "curtain") *ed:layer*(may:layer "led")
  *mm:doorlayer*(may:layer "door") *mm:framelayer*(may:layer "door-frame")
  *mm:headerlayer*(may:layer "opening") *cw:layer*(may:layer "window")))
(defun may:save-profile (/ file row)
 (may:mkdir may:user)
 (if(setq file(open(strcat may:user "layers.lsp")"w""utf8"))
  (progn(write-line(strcat "(setq may:layers '"(vl-prin1-to-string may:layers)")")file)(close file)T)))
(if(findfile(strcat may:user "layers.lsp"))(load(strcat may:user "layers.lsp")))
(defun c:MAYCONFIG (/ role name old)
 (princ "\n角色：wardrobe / cabinet-high / cabinet-low / curtain / led / door / door-frame / opening / window")
 (setq role(strcase(getstring T "\n输入要设置的角色（空格结束）：")T))
 (cond
  ((= role ""))
  ((not(assoc role may:layers))(princ "\n没有这个角色。"))
  (T(setq name(getstring T(strcat "\n目标图层名称 <"(may:layer role)">：")))
   (if(/= name "")
    (if(snvalid name)
     (progn(setq old may:layers may:layers(subst(cons role name)(assoc role may:layers)may:layers))
      (if(may:save-profile)(progn(may:sync)(princ "\n映射已保存；下次绘制时使用，不改已有对象。"))
       (progn(setq may:layers old)(princ "\n保存失败，映射未改变。"))))
     (princ "\n图层名称无效。")))))
 (princ))
(defun c:MAYINFO ()
 (princ(strcat "\nMayCAD Mac " may:version " | 毫米平面绘图 | 通用版"))
 (princ "\nSS XX TT TY D DD F B ZZZ FF YGG YGL YGU GZZ CLPM EDD MM CH QP")
 (princ "\nMAYCONFIG 设置图层映射；MAYINFO 查看版本。") (princ))
(princ)

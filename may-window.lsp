; MayCAD Mac portable public module.
(if(not *cw:layer*)(setq *cw:layer* (may:layer "window")))
(defun cw:z (p)(if(caddr p)(caddr p)0.0))
(defun cw:layer-ok (name / rec)
 (and(setq rec(tblsearch "LAYER" name))(> (cdr(assoc 62 rec))0)
  (= 0(logand 21(cdr(assoc 70 rec))))))
(defun cw:basis (a b c / thick normal along span)
 (if(and a b c(equal(cw:z a)(cw:z b)1e-6)(equal(cw:z a)(cw:z c)1e-6))
  (progn
   (setq thick(distance(list(car a)(cadr a))(list(car b)(cadr b))))
   (if(> thick 1e-6)
    (progn
     (setq normal(list(/(- (car b)(car a))thick)(/(- (cadr b)(cadr a))thick))
      along(list(- (cadr normal))(car normal))
      span(+(*(- (car c)(car a))(car along))(*(- (cadr c)(cadr a))(cadr along))))
     (if(< span 0.0)(setq along(mapcar '- along)span(- span)))
     (if(> span 1e-6)(list a along normal thick span)))))))
(defun cw:discard (/)
 (if cw:building(entmake '((0 . "ENDBLK"))))
 (setq cw:building nil)
 (if(and cw:newblock(tblsearch "BLOCK" cw:newblock))
  (command-s "_.-PURGE" "_Blocks" cw:newblock "_N"))
 (setq cw:newblock nil))
(defun cw:specs (span thick / low high)
 (setq low(/(- thick 50.0)2.0)high(+ low 50.0))
 (list
  (list(list 50.0 low 0.0)(list 50.0 high 0.0)251)
  (list(list(- span 50.0)low 0.0)(list(- span 50.0)high 0.0)251)
  (list(list 0.0 low 0.0)(list span low 0.0)251)
  (list(list 0.0 high 0.0)(list span high 0.0)251)
  (list '(0.0 0.0 0.0)(list span 0.0 0.0)nil)
  (list(list 0.0 thick 0.0)(list span thick 0.0)nil)))
(defun cw:insert (basis layer / thick span along normal sign name count ok spec result)
 (if(and basis(cw:layer-ok layer)(> (nth 3 basis)50.0)(> (nth 4 basis)100.0))
  (progn
   (setq thick(nth 3 basis)span(nth 4 basis)along(cadr basis)normal(caddr basis)
    sign(if(< (-(* (car along)(cadr normal))(* (cadr along)(car normal)))0.0)-1.0 1.0)
    count 1 name "CH_1")
   (while(tblsearch "BLOCK" name)(setq count(1+ count)name(strcat "CH_"(itoa count))))
   (setq cw:newblock name
    ok(entmake(list '(0 . "BLOCK")'(100 . "AcDbEntity")'(8 . "0")
     '(100 . "AcDbBlockBegin")(cons 2 name)'(70 . 0)'(10 0.0 0.0 0.0)))
    cw:building(if ok T nil))
   (foreach spec(cw:specs span thick)
    (if ok(setq ok(entmake(append(list '(0 . "LINE")'(100 . "AcDbEntity")'(8 . "0"))
     (if(caddr spec)(list(cons 62(caddr spec)))nil)
     (list '(100 . "AcDbLine")(cons 10(car spec))(cons 11(cadr spec))))))))
   (if cw:building
    (progn(if(not(entmake '((0 . "ENDBLK"))))(setq ok nil))(setq cw:building nil)))
   (if ok
    (if(entmake(list '(0 . "INSERT")'(100 . "AcDbEntity")(cons 8 layer)
     '(100 . "AcDbBlockReference")(cons 2 name)(cons 10(car basis))
     '(41 . 1.0)(cons 42 sign)'(43 . 1.0)(cons 50(atan(cadr along)(car along)))))
     (setq result(entlast))))
   (if result(setq cw:newblock nil)(cw:discard))))
 result)
(defun c:CH (/ *error* a b c basis made undo stop cw:newblock cw:building)
 (defun *error* (msg)
  (if undo
   (progn(if made(entdel made))(cw:discard)(command-s "_.UNDO" "_End")))
  (if(and msg(not(wcmatch(strcase msg)"*CANCEL*,*QUIT*,*EXIT*,*取消*,*中断*")))
   (princ(strcat "\nCH：" msg)))
  (princ))
 (may:prepare "window")
 (cond
  ((not(cw:layer-ok *cw:layer*))
   (princ(strcat "\n窗图层 " *cw:layer* " 不存在、关闭、冻结或锁定。")))
  ((< (abs(caddr(trans '(0.0 0.0 1.0)1 0 T)))0.999999)
   (princ "\n当前UCS倾斜，请先切换到平面UCS。"))
  (T
   (princ "\nCH：三点量墙厚和窗宽；玻璃居中50，两端框50；空格结束。")
   (while(not stop)
    (setq a(getpoint "\n窗起点（墙的一面）："))
    (if(not a)(setq stop T)
     (progn
      (setq b(getpoint a "\n同一洞口边的对侧墙面点（量墙厚）："))
      (if(not b)(setq stop T)
       (progn
        (setq c(getpoint a "\n沿墙拾取窗末端（定窗宽）："))
        (if(not c)(setq stop T)
         (progn
          (setq basis(cw:basis(trans a 1 0)(trans b 1 0)(trans c 1 0)))
          (if(or(not basis)(<= (nth 3 basis)50.0)(<= (nth 4 basis)100.0))(princ "\n点位须同高，墙厚须大于50mm，窗宽须大于100mm。")
           (progn
            (command-s "_.UNDO" "_Begin")(setq undo T)
            (setq made(cw:insert basis *cw:layer*))
            (command-s "_.UNDO" "_End")(setq undo nil)
            (if made(princ "\n窗已成块生成。") (princ "\n生成失败，本次未保留窗线。"))
            (setq made nil))))))))))))
 (princ))
(princ)

; MayCAD Mac portable public module.
(if (not *yg:depth*) (setq *yg:depth* 600.0))
(defun yg:add (a b) (mapcar '+ a b))
(defun yg:sub (a b) (mapcar '- a b))
(defun yg:mul (a s) (mapcar '(lambda(x)(* x s)) a))
(defun yg:dot (a b) (+ (* (car a)(car b)) (* (cadr a)(cadr b))))
(defun yg:xy (p) (list (car p)(cadr p)))
(defun yg:gpoly (pts closed color) (list pts closed color))
(defun yg:gline (p q color) (yg:gpoly (list p q) nil color))

(defun yg:hangers (start finish dep swap / n step i x pts q out)
 (if(and(> (- finish start)140.0)(>= dep 300.0))
  (progn(setq n(max 1(fix(/(- finish start)150.0)))step(/(- finish start)n)i 0)
   (repeat n
    (setq x(+ start(*(+ i 0.5)step))
     pts(list(list(- x 35.0)75.0)(list(+ x 35.0)(- dep 75.0))
              (list(+ x 25.0)(- dep 75.0))(list(- x 45.0)75.0)))
    (if swap(setq pts(mapcar '(lambda(q)(list(cadr q)(car q)))pts)))
    (setq out(cons(append(yg:gpoly pts T 8)'(T))out)i(1+ i)))))out)
(defun yg:straight (w dep / result)
 (if (or (<= w 130.0)(< dep 100.0)) nil
 (progn
  (setq result (list
   (yg:gpoly (list '(0.0 0.0)(list w 0.0)(list w dep)(list 0.0 dep)) T nil)
   (yg:gline '(50.0 18.0)(list (- w 50.0) 18.0) 8)
   (yg:gline '(50.0 0.0)(list 50.0 dep) nil)
   (yg:gline (list (- w 50.0) 0.0)(list (- w 50.0) dep) nil)
   (yg:gline (list 50.0 (- dep 25.0))(list (- w 50.0)(- dep 25.0)) 8)
   (yg:gline (list 65.0 (- (/ dep 2.0) 12.5))(list (- w 65.0)(- (/ dep 2.0) 12.5)) 8)
   (yg:gline (list 65.0 (+ (/ dep 2.0) 12.5))(list (- w 65.0)(+ (/ dep 2.0) 12.5)) 8)))
  (append result (yg:hangers 65.0 (- w 65.0) dep nil)))))
(defun yg:lshape (a b dep / result)
 (if (or (<= a (+ dep 130.0))(<= b (+ dep 130.0))(< dep 100.0)) nil
 (progn
  (setq result (list
   (yg:gpoly (list '(0.0 0.0)(list a 0.0)(list a dep)(list dep dep)(list dep b)(list 0.0 b)) T nil)
   (yg:gline '(18.0 18.0)(list (- a 50.0) 18.0) 8)
   (yg:gline '(18.0 18.0)(list 18.0 (- b 50.0)) 8)
   (yg:gline (list (- a 50.0) 0.0)(list (- a 50.0) dep) nil)
   (yg:gline (list 0.0 (- b 50.0))(list dep (- b 50.0)) nil)
   (yg:gline (list dep (- dep 25.0))(list (- a 50.0)(- dep 25.0)) 8)
   (yg:gline (list (- dep 25.0) dep)(list (- dep 25.0)(- b 50.0)) 8)
   (yg:gline (list (+ dep 15.0)(- (/ dep 2.0) 12.5))(list (- a 65.0)(- (/ dep 2.0) 12.5)) 8)
   (yg:gline (list (+ dep 15.0)(+ (/ dep 2.0) 12.5))(list (- a 65.0)(+ (/ dep 2.0) 12.5)) 8)
   (yg:gline (list (- (/ dep 2.0) 12.5)(+ dep 15.0))(list (- (/ dep 2.0) 12.5)(- b 65.0)) 8)
   (yg:gline (list (+ (/ dep 2.0) 12.5)(+ dep 15.0))(list (+ (/ dep 2.0) 12.5)(- b 65.0)) 8)))
  (append result (yg:hangers (+ dep 65.0)(- a 65.0) dep nil) (yg:hangers (+ dep 65.0)(- b 65.0) dep T)))))
(defun yg:layer-ok ()(or(not(tblsearch "LAYER"(may:layer "wardrobe")))(may:layer-ok(may:layer "wardrobe"))))
(defun yg:make-layer ()(may:prepare "wardrobe"))
(defun yg:dash-type ()
 (if (not (tblsearch "LTYPE" "MAY_YGG_DASH"))
  (entmake '((0 . "LTYPE")(100 . "AcDbSymbolTableRecord")(100 . "AcDbLinetypeTableRecord")(2 . "MAY_YGG_DASH")(70 . 0)(3 . "Wardrobe clothes dash")(72 . 65)(73 . 2)(40 . 48.0)(49 . 30.0)(74 . 0)(49 . -18.0)(74 . 0))) T))
(defun yg:emit-poly (spec / pts color closed d dashed)
 (setq pts(car spec) closed(cadr spec) color(caddr spec) dashed(cadddr spec))
 (setq d (append (list '(0 . "LWPOLYLINE")'(100 . "AcDbEntity")(cons 8(may:layer "wardrobe")))
  (if color (list(cons 62 color)) nil)
  (if dashed (list '(6 . "MAY_YGG_DASH")(cons 48 (/ 1.0 (max 1e-9 (getvar "LTSCALE"))))) nil)
  (list '(100 . "AcDbPolyline")(cons 90(length pts))(cons 70(+ (if closed 1 0) (if dashed 128 0))))
  (mapcar '(lambda(p)(cons 10 p)) pts)))
 (entmake d))

(defun c:YGG (/ *error* points got done dep value side result undo)
 (defun *error* (msg)
  (if undo (command-s "_.UNDO" "_End"))
  (if (and msg(not(wcmatch(strcase msg)"*CANCEL*,*QUIT*,*EXIT*,*取消*,*中断*"))) (princ(strcat "\n" msg))) (princ))
 (setq points nil dep *yg:depth*)
 (princ "\nYGG：依次点背墙端点；两点后空格画一字，第三点画L型（首点为转角）。S设置柜深。")
 (while (and(not done)(< (length points)3))
  (initget "S")
  (setq got(getpoint (cond ((not points)"\n起点/转角 [设置柜深(S)]：") ((= 1(length points))"\n第一边端点 [设置柜深(S)]：") (T "\n另一边端点 [设置柜深(S)] <空格=一字>："))))
  (cond
   ((= 'STR(type got)) (initget 6) (setq value(getreal(strcat "\n柜体深度 <"(rtos dep 2 0)">：")))
    (if value (if(>= value 100.0)(setq dep value *yg:depth* value)(princ "\n柜深不能小于100mm。"))))
   ((not got)(setq done T))
   (T (setq points(append points(list(trans got 1 0)))))))
 (if (= 2(length points))
  (if(setq side(getpoint "\n点柜体向哪一侧伸出："))(setq side(trans side 1 0))))
 (if (or (= 3(length points))(and (= 2(length points)) side))
  (progn
   (command-s "_.UNDO" "_Begin")(setq undo T)
   (setq result(yg:make points dep side))
   (command-s "_.UNDO" "_End")(setq undo nil)
   (if result(princ "\n衣柜完成。"))))
 (princ))
(princ)
(setq yg:dynamic-version "2026-10-21.1")
(if (not *yg:mode*) (setq *yg:mode* "I"))
(defun ygd:rect (x0 y0 x1 y1)
 (yg:gpoly (list(list x0 y0)(list x1 y0)(list x1 y1)(list x0 y1)) T nil))
(defun ygd:shift-spec (spec dx dy / pts)
 (setq pts(mapcar '(lambda(p)(list(+ dx(car p))(+ dy(cadr p)))) (car spec)))
 (cons pts(cdr spec)))
(defun ygd:hangers-at (lo hi dep swap dx dy)
 (mapcar '(lambda(s)(ygd:shift-spec s dx dy))(yg:hangers lo hi dep swap)))
(defun ygd:ushape (a b d / r)
 (if (and (> a(+(* 2 d)130.0))(> b(+ d 130.0)))
 (progn
  (setq r(list
   (yg:gpoly(list '(0.0 0.0)(list a 0.0)(list a b)(list(- a d)b)(list(- a d)d)(list d d)(list d b)(list 0.0 b)) T nil)
   (yg:gpoly(list(list 18.0 b)'(18.0 18.0)(list(- a 18.0)18.0)(list(- a 18.0)b)) nil 8)
   (yg:gline(list 0.0(- b 50.0))(list d(- b 50.0))nil)
   (yg:gline(list(- a d)(- b 50.0))(list a(- b 50.0))nil)
   (yg:gline(list d(- d 25.0))(list(- a d)(- d 25.0))8)
   (yg:gline(list(- d 25.0)d)(list(- d 25.0)(- b 50.0))8)
   (yg:gline(list(+(- a d)25.0)d)(list(+(- a d)25.0)(- b 50.0))8)
   (yg:gline(list(+ d 15.0)(-(/ d 2.0)12.5))(list(- a d 15.0)(-(/ d 2.0)12.5))8)
   (yg:gline(list(+ d 15.0)(+(/ d 2.0)12.5))(list(- a d 15.0)(+(/ d 2.0)12.5))8)
   (yg:gline(list(-(/ d 2.0)12.5)(+ d 15.0))(list(-(/ d 2.0)12.5)(- b 65.0))8)
   (yg:gline(list(+(/ d 2.0)12.5)(+ d 15.0))(list(+(/ d 2.0)12.5)(- b 65.0))8)
   (yg:gline(list(- a(/ d 2.0)12.5)(+ d 15.0))(list(- a(/ d 2.0)12.5)(- b 65.0))8)
   (yg:gline(list(+(- a(/ d 2.0))12.5)(+ d 15.0))(list(+(- a(/ d 2.0))12.5)(- b 65.0))8)))
  (append r
   (yg:hangers(+ d 65.0)(- a d 65.0)d nil)
   (yg:hangers(+ d 65.0)(- b 65.0)d T)
   (ygd:hangers-at(+ d 65.0)(- b 65.0)d T(- a d)0.0)))))
(defun ygd:turn-point (p face a b)
 (cond((= face 1)(list(- a(cadr p))(car p)))
      ((= face 2)(list(- a(car p))(- b(cadr p))))
      ((= face 3)(list(cadr p)(- b(car p))))(T p)))
(defun ygd:specs (mode a b dep face / base aa bb)
 (if(>= dep 100.0)
 (progn
  (setq aa a bb b)
  (if(member face '(1 3))(setq aa b bb a))
  (setq base(cond((= mode "I")(yg:straight a dep))
                 ((= mode "L")(yg:lshape aa bb dep))
                 ((= mode "U")(ygd:ushape aa bb dep))))
  (if(and base(member mode '("L" "U")))
   (mapcar '(lambda(s)(cons(mapcar '(lambda(p)(ygd:turn-point p face a b))(car s))(cdr s)))base)
   base))))
(defun ygd:local-point (p origin ang sx sy / x y)
 (setq x(* sx(car p)) y(* sy(cadr p)))
 (list(+ (car origin)(-(* x(cos ang))(* y(sin ang))))
       (+ (cadr origin)(+(* x(sin ang))(* y(cos ang))))
       (if(caddr origin)(caddr origin)0.0)))
(defun ygd:preview (specs origin ang sx sy / vectors s pts p q col)
 (foreach s specs
  (setq pts(mapcar '(lambda(p)(ygd:local-point p origin ang sx sy))(car s))
        col(if(caddr s)(caddr s)3))
  (if(cadr s)(setq pts(append pts(list(car pts)))))
  (while(cdr pts)
   (setq p(car pts)q(cadr pts) vectors(cons col(cons p(cons q vectors))) pts(cdr pts))))
 (redraw)
 (if vectors(grvecs vectors))
 (length vectors))
(defun ygd:store (specs origin ang sx sy / name n ok begun e s)
 (cond
  ((not specs)(princ "\n尺寸不足，尚未生成。")nil)
  ((not(yg:layer-ok))(princ "\n衣柜图层已关闭、冻结或锁定，请先恢复。")nil)
  (T
   (setq n 1 name "YGG_1")
   (while(tblsearch "BLOCK" name)(setq n(1+ n)name(strcat "YGG_"(itoa n))))
   (setq ok(and(yg:make-layer)(yg:dash-type)))
   (if ok(setq ok(entmake(list '(0 . "BLOCK")(cons 8(may:layer "wardrobe"))(cons 2 name)'(70 . 0)'(10 0.0 0.0 0.0)))begun ok))
   (foreach s specs(if ok(setq ok(yg:emit-poly s))))
   (if begun(if(not(entmake '((0 . "ENDBLK"))))(setq ok nil)))
   (if ok(setq ok(entmake(list '(0 . "INSERT")(cons 8(may:layer "wardrobe"))(cons 2 name)(cons 10 origin)(cons 41 sx)(cons 42 sy)'(43 . 1.0)(cons 50 ang)))))
   (if ok(entlast)
    (progn
     (if(tblsearch "BLOCK" name)(command-s "_.-PURGE" "_B" name "_N"))
     (princ "\n柜体生成失败，本次没有插入柜体。")nil)))))
(defun ygd:snap (p / bits modes hit tol screen item)
 (setq bits(getvar "OSMODE")modes "")
 (if(= 0(logand bits 16384))
  (foreach item '((1 . "END")(2 . "MID")(4 . "CEN")(8 . "NOD")(16 . "QUA")(32 . "INT")(64 . "INS")(128 . "PER")(256 . "TAN")(512 . "NEA")(2048 . "APPINT"))
   (if(/= 0(logand bits(car item)))(setq modes(strcat modes(if(= modes "")"" ",")(cdr item))))))
 (if(/= modes "")(setq hit(osnap p modes)))
 (setq screen(getvar "SCREENSIZE")tol(* (max 8(getvar "APERTURE"))(/ (getvar "VIEWSIZE")(max 1(cadr screen)))))
 (if(and hit(<= (distance(yg:xy hit)(yg:xy p))tol))hit p))
(defun ygd:params (origin cursor ang mode dep flip / delta x y sx sy useang)
 (setq delta(yg:sub(yg:xy cursor)(yg:xy origin))
       x(+(*(car delta)(cos ang))(*(cadr delta)(sin ang)))
       y(+(*(-(car delta))(sin ang))(*(cadr delta)(cos ang))) useang ang)
 (if(and(= mode "I")(>(abs y)(abs x)))
  (setq useang(+ ang(/ pi 2.0))delta x x y y(- delta)))
 (setq sx(if(< x 0.0)-1.0 1.0)sy(if(< y 0.0)-1.0 1.0))
 (if(and(= mode "I")(= 1(rem flip 2)))(setq sy(- sy)))
 (list(abs x)(if(= mode "I")dep(abs y))useang sx sy))
(defun ygd:mode-name (mode)
 (cond((= mode "I")"一字")((= mode "L")"L型")((= mode "U")"U型")))
(defun ygd:prompt (mode dep face)
 (princ(strcat "\n"(ygd:mode-name mode)"柜：移动鼠标预览，左键/空格确认；I一字/L转角/U三面，F换方向，S柜深，R旋转，Esc取消。柜深="(rtos dep 2 0)"mm。")))
(defun ygd:depth (dep / value)
 (initget 6)
 (setq value(getdist(strcat "\n柜深 <"(rtos dep 2 0)">：")))
 (cond((not value)dep)((>= value 100.0)value)(T(princ "\n柜深不能小于100mm。")dep)))
(defun ygd:parse-size (buffer mode / i split first second)
 (setq i 1)
 (while(and(<= i(strlen buffer))(not split))
  (if(member(substr buffer i 1)'("," "x" "X"))(setq split i))
  (setq i(1+ i)))
 (if split
  (progn(setq first(distof(substr buffer 1(1- split))2)second(distof(substr buffer(1+ split))2))
   (if(and first second(> first 0.0)(> second 0.0))(list first second)))
  (if(and(= mode "I")(setq first(distof buffer 2))(> first 0.0))(list first *yg:depth*))))
(defun ygd:run (initial / *error* mode dep ang origin got done evt code val cursor params specs face result undo buffer dims newang worldaxis worldorigin previous)
 (defun *error* (msg)
  (redraw)
  (if undo(command-s "_.UNDO" "_End"))
  (if(and msg(not(wcmatch(strcase msg)"*CANCEL*,*QUIT*,*EXIT*,*取消*,*中断*,*BREAK*")))(princ(strcat "\n"msg)))
  (princ))
 (setq mode(if initial initial *yg:mode*)dep *yg:depth* ang 0.0 face 0 buffer "")
 (if(not(equal(trans '(0.0 0.0 1.0)1 0 T)'(0.0 0.0 1.0)1e-6))
  (princ "\n当前UCS不在平面上，请切回平面UCS后使用。")
  (progn
   (princ "\nYGG动态衣柜：点一个角、拉出范围、再点确认。I一字/L型/U型。")
   (while(not(or origin done))
    (initget "I L U S R")
    (setq got(getpoint(strcat "\n点起始角 [一字(I)/L型(L)/U型(U)/柜深(S)/旋转(R)] <"(ygd:mode-name mode)">：")))
    (cond
     ((not got)(setq done T))
     ((= 'STR(type got))
      (cond((= got "S")(setq dep(ygd:depth dep)*yg:depth* dep))
           ((= got "R")(setq newang(getangle "\n指定柜体沿墙方向 <0>："))(if newang(setq ang newang)))
           (T(setq mode got *yg:mode* got))))
     (T(setq origin got))))
   (if origin
    (progn
     (setq *yg:mode* mode cursor origin)
     (ygd:prompt mode dep face)
     (while(not done)
      (setq evt(grread T 15 0)code(car evt)val(cadr evt))
      (cond
       ((member code '(3 5))
        (setq cursor(ygd:snap val)
              params(ygd:params origin cursor ang mode dep face)
              specs(ygd:specs mode(car params)(cadr params)dep(rem face 4)))
        (if specs(ygd:preview specs origin(nth 2 params)(nth 3 params)(nth 4 params))(redraw))
        (if(= code 3)
         (if specs(setq done T)(princ "\n范围太小，请继续拉大；L每边须超过柜深+130，U型须留出中间空间。"))))
       ((= code 2)
        (cond
         ((= val 27)(setq done T specs nil))
         ((member val '(73 105 76 108 85 117))
          (setq mode(strcase(chr val))*yg:mode* mode buffer ""))
         ((member val '(70 102))(setq face(rem(1+ face)4)buffer ""))
         ((member val '(83 115))
          (redraw)(setq dep(ygd:depth dep)*yg:depth* dep buffer ""))
         ((member val '(82 114))
          (redraw)(setq newang(getangle origin "\n点取沿墙方向："))
          (if newang(setq ang newang))(setq buffer ""))
         ((= val 8)(if(> (strlen buffer)0)(setq buffer(substr buffer 1(1- (strlen buffer))))))
         ((or(member val '(13 32)))
          (if(/= buffer "")
           (progn
            (setq dims(ygd:parse-size buffer mode))
            (if dims
             (progn
              (setq params(list(car dims)(if(= mode "I")dep(cadr dims))(if params(nth 2 params)ang)(if params(nth 3 params)1.0)(if params(nth 4 params)1.0))
                    specs(ygd:specs mode(car params)(cadr params)dep(rem face 4)))
              (if specs(setq done T)(princ "\n尺寸不足，请重新输入。")))
             (princ "\n请输入长,宽，例如3000,2400；一字柜可只输入长度。"))
            (setq buffer ""))
           (if specs(setq done T))))
         ((or(and(>= val 48)(<= val 57))(member val '(46 44 120 88)))
          (setq buffer(strcat buffer(chr val)))(princ(chr val))))
        (if(not done)
         (progn
          (setq params(ygd:params origin cursor ang mode dep face)
                specs(ygd:specs mode(car params)(cadr params)dep(rem face 4)))
          (if specs(ygd:preview specs origin(nth 2 params)(nth 3 params)(nth 4 params))(redraw))
          (if(member val '(73 105 76 108 85 117 70 102 83 115 82 114))(ygd:prompt mode dep face)))))
       ((member code '(11 25))(setq done T specs nil))))
     (redraw)
     (if specs
      (progn
       (setq worldorigin(trans origin 1 0)
             worldaxis(trans(list(cos(nth 2 params))(sin(nth 2 params))0.0)1 0 T))
       (command-s "_.UNDO" "_Begin")(setq undo T)
       (setq result(ygd:store specs worldorigin(atan(cadr worldaxis)(car worldaxis))(nth 3 params)(nth 4 params)))
       (command-s "_.UNDO" "_End")(setq undo nil)
       (if result(princ(strcat "\n"(ygd:mode-name mode)"柜完成："(rtos(car params)2 0)"×"(rtos(cadr params)2 0)"mm。"))))))))
 )
 (princ))

(defun c:YGL ()(ygd:run "L"))
(defun c:YGU ()(ygd:run "U"))
(princ)
